--
-- TELESTE-HDONE-MIB.mib
-- MIB generated by MG-SOFT Visual MIB Builder Version 4.0 Build 349
-- Wednesday, August 17, 2005 at 09:16:46
--

-- ****************************************************************************
-- Copyright (c) 2005-2006 by:
-- 
-- Teleste Corporation
-- Seponkatu 1
-- FIN-20660 Littoinen, Finland
-- tel. +358 2 2605 611
-- url: http://www.teleste.com
-- 
-- Module Name:   TELESTE-HDONE-MIB
-- 
-- Description:   MIB module describing HDO NE objects
-- 
-- Revision History:
-- -----------------
-- 1.01, 17.8.2005, Matti Susi
-- - nec node number changed to 100
-- 
-- 1.0, 12.8.2005, Matti Susi
-- - First official release
-- 
-- ****************************************************************************

	TELESTE-HDONE-MIB DEFINITIONS ::= BEGIN
 
		IMPORTS
			OBJECT-TYPE			
				FROM RFC-1212			
			experimental, IpAddress			
				FROM RFC1155-SMI			
			DisplayString			
				FROM RFC1213-MIB			
			oemodules			
				FROM TELESTE-HDO-MIB;
	
	
--
-- Type definitions
--
	
		NESlotValue ::= INTEGER (0..50)

		ModuleWidthValue ::= INTEGER (0..4)

		PerceivedSeverityValue ::= INTEGER
			{
			notification(0),
			notused1(1),
			alarm(2),
			warning(3),
			notused2(4),
			clear(5)
			}

		GpioType ::= INTEGER
			{
			gpioTypeNotSupported(1),
			gpioTypeInputOnly(2),
			gpioTypeInputOrOutput(3),
			gpioTypeOutputOnly(4)
			}

-- Port is not supported be this type of NEC
		GpioMode ::= INTEGER
			{
			gpioModeInput(1),
			gpioModeInputIsNotify(2),
			gpioModeInputIsWarning(3),
			gpioModeInputIsAlarm(4),
			gpioModeOutputOnAnyAlarm(5),
			gpioModeOutputOnAnyWarning(6)
			}

-- Only used for web interface
-- Not usable for all gpio ports
		GpioLogicLevel ::= INTEGER
			{
			gpioLevelActiveHigh(1),
			gpioLevelActiveLow(2)
			}

		NESlotWriteValue ::= INTEGER (-1..50)

		TruthValue ::= INTEGER
			{
			true(1),
			false(2)
			}

-- Default setting until NECE Software 1.10
		TrapVerifyTimeoutValue ::= INTEGER (30..600)

		TrapAccumulationTimeValue ::= INTEGER (0..60)

		HmsTrapsComplianceValue ::= INTEGER
			{
			fullCompliant(1),
			minorCompliant(2)
			}

-- Default setting until NECE Software 1.10
		HfcInventoryFormatValue ::= INTEGER
			{
			format_DKS_T12_9(1),
			format_T_Nova_E531i(2)
			}

	
--
-- Node definitions
--
	
		-- 1.3.6.1.4.1.3715.14.2.100
		nec OBJECT IDENTIFIER ::= { oemodules 100 }

		
		-- 1.3.6.1.4.1.3715.14.2.100.1
		neceCommon OBJECT IDENTIFIER ::= { nec 1 }

		
		-- 1.3.6.1.4.1.3715.14.2.100.1.1
		neceCommonNumberOfModules OBJECT-TYPE
			SYNTAX INTEGER
			ACCESS read-only
			STATUS mandatory
			DESCRIPTION
				"Number of modules in table."
			::= { neceCommon 1 }

		
-- NEC common table
		-- 1.3.6.1.4.1.3715.14.2.100.1.2
		neceCommonTable OBJECT-TYPE
			SYNTAX SEQUENCE OF NeceCommonEntry
			ACCESS not-accessible
			STATUS mandatory
			DESCRIPTION
				"The table contains all modules of the nece-type in the NE"
			::= { neceCommon 2 }

		
-- Table row definition
		-- 1.3.6.1.4.1.3715.14.2.100.1.2.1
		neceCommonEntry OBJECT-TYPE
			SYNTAX NeceCommonEntry
			ACCESS not-accessible
			STATUS mandatory
			DESCRIPTION
				"Common-Values for a module."
			INDEX { neceNESlot }
			::= { neceCommonTable 1 }

		
		NeceCommonEntry ::=
			SEQUENCE { 
				neceNESlot
					NESlotValue,
				neceCommonType
					DisplayString,
				neceCommonDescr
					DisplayString,
				neceCommonFirmwareId
					DisplayString,
				neceCommonModuleWidth
					ModuleWidthValue
			 }

		-- 1.3.6.1.4.1.3715.14.2.100.1.2.1.1
		neceNESlot OBJECT-TYPE
			SYNTAX NESlotValue
			ACCESS read-only
			STATUS mandatory
			DESCRIPTION
				"The slot number of the chassis for which this
				entry contains management information."
			::= { neceCommonEntry 1 }

		
		-- 1.3.6.1.4.1.3715.14.2.100.1.2.1.2
		neceCommonType OBJECT-TYPE
			SYNTAX DisplayString (SIZE (0..32))
			ACCESS read-only
			STATUS mandatory
			DESCRIPTION
				"The type of physical module. modSlotEmpty indicates 
				an empty slot.  A Value of modSlotUnknown indicates
				that the type of module is unknown."
			::= { neceCommonEntry 2 }

		
		-- 1.3.6.1.4.1.3715.14.2.100.1.2.1.3
		neceCommonDescr OBJECT-TYPE
			SYNTAX DisplayString
			ACCESS read-write
			STATUS mandatory
			DESCRIPTION
				"A textual description of the module.
				If not available, this Value should be
				set to a zero length string."
			::= { neceCommonEntry 3 }

		
		-- 1.3.6.1.4.1.3715.14.2.100.1.2.1.4
		neceCommonFirmwareId OBJECT-TYPE
			SYNTAX DisplayString (SIZE (0..32))
			ACCESS read-only
			STATUS mandatory
			DESCRIPTION
				"The firmware Id of the module."
			::= { neceCommonEntry 4 }

		
		-- 1.3.6.1.4.1.3715.14.2.100.1.2.1.5
		neceCommonModuleWidth OBJECT-TYPE
			SYNTAX ModuleWidthValue
			ACCESS read-only
			STATUS mandatory
			DESCRIPTION
				"The width of the module."
			::= { neceCommonEntry 5 }

		
		-- 1.3.6.1.4.1.3715.14.2.100.2
		neceStates OBJECT IDENTIFIER ::= { nec 2 }

		
-- NEC status table
		-- 1.3.6.1.4.1.3715.14.2.100.2.1
		neceStatesTable OBJECT-TYPE
			SYNTAX SEQUENCE OF NeceStatesEntry
			ACCESS not-accessible
			STATUS mandatory
			::= { neceStates 1 }

		
-- Table row definition
		-- 1.3.6.1.4.1.3715.14.2.100.2.1.1
		neceStatesEntry OBJECT-TYPE
			SYNTAX NeceStatesEntry
			ACCESS not-accessible
			STATUS mandatory
			DESCRIPTION
				"Alarms for a module."
			INDEX { neceNESlot }
			::= { neceStatesTable 1 }

		
		NeceStatesEntry ::=
			SEQUENCE { 
				neceStatesGpInput1
					PerceivedSeverityValue,
				neceStatesGpInput2
					PerceivedSeverityValue,
				neceStatesGpInput3
					PerceivedSeverityValue,
				neceStatesGpInput4
					PerceivedSeverityValue,
				neceStatesGpInput5
					PerceivedSeverityValue,
				neceStatesGpInput6
					PerceivedSeverityValue,
				neceStatesGpInput7
					PerceivedSeverityValue,
				neceStatesGpInput8
					PerceivedSeverityValue,
				neceStatesGpInput9
					PerceivedSeverityValue,
				neceStatesGpInput10
					PerceivedSeverityValue,
				neceStatesGpInput11
					PerceivedSeverityValue,
				neceStatesGpInput12
					PerceivedSeverityValue
			 }

		-- 1.3.6.1.4.1.3715.14.2.100.2.1.1.1
		neceStatesGpInput1 OBJECT-TYPE
			SYNTAX PerceivedSeverityValue
			ACCESS read-only
			STATUS mandatory
			DESCRIPTION
				"State of general purpose input no. 1."
			::= { neceStatesEntry 1 }

		
		-- 1.3.6.1.4.1.3715.14.2.100.2.1.1.2
		neceStatesGpInput2 OBJECT-TYPE
			SYNTAX PerceivedSeverityValue
			ACCESS read-only
			STATUS mandatory
			DESCRIPTION
				"State of general purpose input no. 2."
			::= { neceStatesEntry 2 }

		
		-- 1.3.6.1.4.1.3715.14.2.100.2.1.1.3
		neceStatesGpInput3 OBJECT-TYPE
			SYNTAX PerceivedSeverityValue
			ACCESS read-only
			STATUS mandatory
			DESCRIPTION
				"State of general purpose input no. 3."
			::= { neceStatesEntry 3 }

		
		-- 1.3.6.1.4.1.3715.14.2.100.2.1.1.4
		neceStatesGpInput4 OBJECT-TYPE
			SYNTAX PerceivedSeverityValue
			ACCESS read-only
			STATUS mandatory
			DESCRIPTION
				"State of general purpose input no. 4."
			::= { neceStatesEntry 4 }

		
		-- 1.3.6.1.4.1.3715.14.2.100.2.1.1.5
		neceStatesGpInput5 OBJECT-TYPE
			SYNTAX PerceivedSeverityValue
			ACCESS read-only
			STATUS mandatory
			DESCRIPTION
				"State of general purpose input no. 5."
			::= { neceStatesEntry 5 }

		
		-- 1.3.6.1.4.1.3715.14.2.100.2.1.1.6
		neceStatesGpInput6 OBJECT-TYPE
			SYNTAX PerceivedSeverityValue
			ACCESS read-only
			STATUS mandatory
			DESCRIPTION
				"State of general purpose input no. 6."
			::= { neceStatesEntry 6 }

		
		-- 1.3.6.1.4.1.3715.14.2.100.2.1.1.7
		neceStatesGpInput7 OBJECT-TYPE
			SYNTAX PerceivedSeverityValue
			ACCESS read-only
			STATUS mandatory
			DESCRIPTION
				"State of general purpose input no. 7."
			::= { neceStatesEntry 7 }

		
		-- 1.3.6.1.4.1.3715.14.2.100.2.1.1.8
		neceStatesGpInput8 OBJECT-TYPE
			SYNTAX PerceivedSeverityValue
			ACCESS read-only
			STATUS mandatory
			DESCRIPTION
				"State of general purpose input no. 8."
			::= { neceStatesEntry 8 }

		
		-- 1.3.6.1.4.1.3715.14.2.100.2.1.1.9
		neceStatesGpInput9 OBJECT-TYPE
			SYNTAX PerceivedSeverityValue
			ACCESS read-only
			STATUS mandatory
			DESCRIPTION
				"State of general purpose input no. 9."
			::= { neceStatesEntry 9 }

		
		-- 1.3.6.1.4.1.3715.14.2.100.2.1.1.10
		neceStatesGpInput10 OBJECT-TYPE
			SYNTAX PerceivedSeverityValue
			ACCESS read-only
			STATUS mandatory
			DESCRIPTION
				"State of general purpose input no. 10."
			::= { neceStatesEntry 10 }

		
		-- 1.3.6.1.4.1.3715.14.2.100.2.1.1.11
		neceStatesGpInput11 OBJECT-TYPE
			SYNTAX PerceivedSeverityValue
			ACCESS read-only
			STATUS mandatory
			DESCRIPTION
				"State of general purpose input no. 11."
			::= { neceStatesEntry 11 }

		
		-- 1.3.6.1.4.1.3715.14.2.100.2.1.1.12
		neceStatesGpInput12 OBJECT-TYPE
			SYNTAX PerceivedSeverityValue
			ACCESS read-only
			STATUS mandatory
			DESCRIPTION
				"State of general purpose input no. 12."
			::= { neceStatesEntry 12 }

		
		-- 1.3.6.1.4.1.3715.14.2.100.3
		neceConfiguration OBJECT IDENTIFIER ::= { nec 3 }

		
-- NEC configuration table
		-- 1.3.6.1.4.1.3715.14.2.100.3.1
		neceConfigurationTable OBJECT-TYPE
			SYNTAX SEQUENCE OF NeceConfigurationEntry
			ACCESS not-accessible
			STATUS mandatory
			::= { neceConfiguration 1 }

		
-- Table row definition
		-- 1.3.6.1.4.1.3715.14.2.100.3.1.1
		neceConfigurationEntry OBJECT-TYPE
			SYNTAX NeceConfigurationEntry
			ACCESS not-accessible
			STATUS mandatory
			INDEX { neceNESlot }
			::= { neceConfigurationTable 1 }

		
		NeceConfigurationEntry ::=
			SEQUENCE { 
				neceConfigGpio1Type
					GpioType,
				neceConfigGpio1Mode
					GpioMode,
				neceConfigGpio1LogicLevel
					GpioLogicLevel,
				neceConfigGpio1Description
					DisplayString,
				neceConfigGpio2Type
					GpioType,
				neceConfigGpio2Mode
					GpioMode,
				neceConfigGpio2LogicLevel
					GpioLogicLevel,
				neceConfigGpio2Description
					DisplayString,
				neceConfigGpio3Type
					GpioType,
				neceConfigGpio3Mode
					GpioMode,
				neceConfigGpio3LogicLevel
					GpioLogicLevel,
				neceConfigGpio3Description
					DisplayString,
				neceConfigGpio4Type
					GpioType,
				neceConfigGpio4Mode
					GpioMode,
				neceConfigGpio4LogicLevel
					GpioLogicLevel,
				neceConfigGpio4Description
					DisplayString,
				neceConfigGpio5Type
					GpioType,
				neceConfigGpio5Mode
					GpioMode,
				neceConfigGpio5LogicLevel
					GpioLogicLevel,
				neceConfigGpio5Description
					DisplayString,
				neceConfigGpio6Type
					GpioType,
				neceConfigGpio6Mode
					GpioMode,
				neceConfigGpio6LogicLevel
					GpioLogicLevel,
				neceConfigGpio6Description
					DisplayString,
				neceConfigGpio7Type
					GpioType,
				neceConfigGpio7Mode
					GpioMode,
				neceConfigGpio7LogicLevel
					GpioLogicLevel,
				neceConfigGpio7Description
					DisplayString,
				neceConfigGpio8Type
					GpioType,
				neceConfigGpio8Mode
					GpioMode,
				neceConfigGpio8LogicLevel
					GpioLogicLevel,
				neceConfigGpio8Description
					DisplayString,
				neceConfigGpio9Type
					GpioType,
				neceConfigGpio9Mode
					GpioMode,
				neceConfigGpio9LogicLevel
					GpioLogicLevel,
				neceConfigGpio9Description
					DisplayString,
				neceConfigGpio10Type
					GpioType,
				neceConfigGpio10Mode
					GpioMode,
				neceConfigGpio10LogicLevel
					GpioLogicLevel,
				neceConfigGpio10Description
					DisplayString,
				neceConfigGpio11Type
					GpioType,
				neceConfigGpio11Mode
					GpioMode,
				neceConfigGpio11LogicLevel
					GpioLogicLevel,
				neceConfigGpio11Description
					DisplayString,
				neceConfigGpio12Type
					GpioType,
				neceConfigGpio12Mode
					GpioMode,
				neceConfigGpio12LogicLevel
					GpioLogicLevel,
				neceConfigGpio12Description
					DisplayString,
				neceConfigNESlotWrite
					NESlotWriteValue,
				neceConfigIpAddress
					IpAddress,
				neceConfigNetmask
					IpAddress,
				neceConfigDefaultrouter
					IpAddress,
				neceConfigTrapReceiver1HostIp
					IpAddress,
				neceConfigTrapReceiver1Community
					DisplayString,
				neceConfigTrapReceiver2HostIp
					IpAddress,
				neceConfigTrapReceiver2to4Community
					DisplayString,
				neceConfigTrapReceiver3HostIp
					IpAddress,
				neceConfigTrapReceiver4HostIp
					IpAddress,
				neceConfigGetCommunity
					DisplayString,
				neceConfigSetCommunity
					DisplayString,
				neceConfigTrapReceiverVerify
					TruthValue,
				neceConfigTrapVerifyReceiverIp
					IpAddress,
				neceConfigTrapVerifyTimeout
					TrapVerifyTimeoutValue,
				neceConfigTrapAccumulationTime
					TrapAccumulationTimeValue,
				neceConfigCableWatchUsed
					TruthValue,
				neceConfigHmsTrapsCompliance
					HmsTrapsComplianceValue,
				neceConfigHmsNotificationsEnable
					TruthValue,
				neceConfigHfcInventoryFormat
					HfcInventoryFormatValue,
				neceConfigFactoryInternal
					TruthValue
			 }

		-- 1.3.6.1.4.1.3715.14.2.100.3.1.1.1
		neceConfigGpio1Type OBJECT-TYPE
			SYNTAX GpioType
			ACCESS read-only
			STATUS mandatory
			DESCRIPTION
				"The type of the general purpose port no. 1"
			::= { neceConfigurationEntry 1 }

		
		-- 1.3.6.1.4.1.3715.14.2.100.3.1.1.2
		neceConfigGpio1Mode OBJECT-TYPE
			SYNTAX GpioMode
			ACCESS read-write
			STATUS mandatory
			DESCRIPTION
				"The mode of the general purpose port no. 1"
			::= { neceConfigurationEntry 2 }

		
		-- 1.3.6.1.4.1.3715.14.2.100.3.1.1.3
		neceConfigGpio1LogicLevel OBJECT-TYPE
			SYNTAX GpioLogicLevel
			ACCESS read-write
			STATUS mandatory
			DESCRIPTION
				"The logic level of the general purpose port no. 1"
			::= { neceConfigurationEntry 3 }

		
		-- 1.3.6.1.4.1.3715.14.2.100.3.1.1.4
		neceConfigGpio1Description OBJECT-TYPE
			SYNTAX DisplayString (SIZE (0..31))
			ACCESS read-write
			STATUS mandatory
			DESCRIPTION
				"A description for the general purpose port no. 1"
			::= { neceConfigurationEntry 4 }

		
--  READONLY !!!
		-- 1.3.6.1.4.1.3715.14.2.100.3.1.1.5
		neceConfigGpio2Type OBJECT-TYPE
			SYNTAX GpioType
			ACCESS read-only
			STATUS mandatory
			DESCRIPTION
				"The type of the general purpose port no. 2"
			::= { neceConfigurationEntry 5 }

		
		-- 1.3.6.1.4.1.3715.14.2.100.3.1.1.6
		neceConfigGpio2Mode OBJECT-TYPE
			SYNTAX GpioMode
			ACCESS read-write
			STATUS mandatory
			DESCRIPTION
				"The mode of the general purpose port no. 2"
			::= { neceConfigurationEntry 6 }

		
		-- 1.3.6.1.4.1.3715.14.2.100.3.1.1.7
		neceConfigGpio2LogicLevel OBJECT-TYPE
			SYNTAX GpioLogicLevel
			ACCESS read-write
			STATUS mandatory
			DESCRIPTION
				"The logic level of the general purpose port no. 2"
			::= { neceConfigurationEntry 7 }

		
		-- 1.3.6.1.4.1.3715.14.2.100.3.1.1.8
		neceConfigGpio2Description OBJECT-TYPE
			SYNTAX DisplayString (SIZE (0..31))
			ACCESS read-write
			STATUS mandatory
			DESCRIPTION
				"A description for the general purpose port no. 2"
			::= { neceConfigurationEntry 8 }

		
--  READONLY !!!
		-- 1.3.6.1.4.1.3715.14.2.100.3.1.1.9
		neceConfigGpio3Type OBJECT-TYPE
			SYNTAX GpioType
			ACCESS read-only
			STATUS mandatory
			DESCRIPTION
				"The type of the general purpose port no. 3"
			::= { neceConfigurationEntry 9 }

		
		-- 1.3.6.1.4.1.3715.14.2.100.3.1.1.10
		neceConfigGpio3Mode OBJECT-TYPE
			SYNTAX GpioMode
			ACCESS read-write
			STATUS mandatory
			DESCRIPTION
				"The mode of the general purpose port no. 3"
			::= { neceConfigurationEntry 10 }

		
		-- 1.3.6.1.4.1.3715.14.2.100.3.1.1.11
		neceConfigGpio3LogicLevel OBJECT-TYPE
			SYNTAX GpioLogicLevel
			ACCESS read-write
			STATUS mandatory
			DESCRIPTION
				"The logic level of the general purpose port no. 3"
			::= { neceConfigurationEntry 11 }

		
		-- 1.3.6.1.4.1.3715.14.2.100.3.1.1.12
		neceConfigGpio3Description OBJECT-TYPE
			SYNTAX DisplayString (SIZE (0..31))
			ACCESS read-write
			STATUS mandatory
			DESCRIPTION
				"A description for the general purpose port no. 3"
			::= { neceConfigurationEntry 12 }

		
--  READONLY !!!
		-- 1.3.6.1.4.1.3715.14.2.100.3.1.1.13
		neceConfigGpio4Type OBJECT-TYPE
			SYNTAX GpioType
			ACCESS read-only
			STATUS mandatory
			DESCRIPTION
				"The type of the general purpose port no. 4"
			::= { neceConfigurationEntry 13 }

		
		-- 1.3.6.1.4.1.3715.14.2.100.3.1.1.14
		neceConfigGpio4Mode OBJECT-TYPE
			SYNTAX GpioMode
			ACCESS read-write
			STATUS mandatory
			DESCRIPTION
				"The mode of the general purpose port no. 4"
			::= { neceConfigurationEntry 14 }

		
		-- 1.3.6.1.4.1.3715.14.2.100.3.1.1.15
		neceConfigGpio4LogicLevel OBJECT-TYPE
			SYNTAX GpioLogicLevel
			ACCESS read-write
			STATUS mandatory
			DESCRIPTION
				"The logic level of the general purpose port no. 4"
			::= { neceConfigurationEntry 15 }

		
		-- 1.3.6.1.4.1.3715.14.2.100.3.1.1.16
		neceConfigGpio4Description OBJECT-TYPE
			SYNTAX DisplayString (SIZE (0..31))
			ACCESS read-write
			STATUS mandatory
			DESCRIPTION
				"A description for the general purpose port no. 4"
			::= { neceConfigurationEntry 16 }

		
--  READONLY !!!
		-- 1.3.6.1.4.1.3715.14.2.100.3.1.1.17
		neceConfigGpio5Type OBJECT-TYPE
			SYNTAX GpioType
			ACCESS read-only
			STATUS mandatory
			DESCRIPTION
				"The type of the general purpose port no. 5"
			::= { neceConfigurationEntry 17 }

		
		-- 1.3.6.1.4.1.3715.14.2.100.3.1.1.18
		neceConfigGpio5Mode OBJECT-TYPE
			SYNTAX GpioMode
			ACCESS read-write
			STATUS mandatory
			DESCRIPTION
				"The mode of the general purpose port no. 5"
			::= { neceConfigurationEntry 18 }

		
		-- 1.3.6.1.4.1.3715.14.2.100.3.1.1.19
		neceConfigGpio5LogicLevel OBJECT-TYPE
			SYNTAX GpioLogicLevel
			ACCESS read-write
			STATUS mandatory
			DESCRIPTION
				"The logic level of the general purpose port no. 5"
			::= { neceConfigurationEntry 19 }

		
		-- 1.3.6.1.4.1.3715.14.2.100.3.1.1.20
		neceConfigGpio5Description OBJECT-TYPE
			SYNTAX DisplayString (SIZE (0..31))
			ACCESS read-write
			STATUS mandatory
			DESCRIPTION
				"A description for the general purpose port no. 5"
			::= { neceConfigurationEntry 20 }

		
--  READONLY !!!
		-- 1.3.6.1.4.1.3715.14.2.100.3.1.1.21
		neceConfigGpio6Type OBJECT-TYPE
			SYNTAX GpioType
			ACCESS read-only
			STATUS mandatory
			DESCRIPTION
				"The type of the general purpose port no. 6"
			::= { neceConfigurationEntry 21 }

		
		-- 1.3.6.1.4.1.3715.14.2.100.3.1.1.22
		neceConfigGpio6Mode OBJECT-TYPE
			SYNTAX GpioMode
			ACCESS read-write
			STATUS mandatory
			DESCRIPTION
				"The mode of the general purpose port no. 6"
			::= { neceConfigurationEntry 22 }

		
		-- 1.3.6.1.4.1.3715.14.2.100.3.1.1.23
		neceConfigGpio6LogicLevel OBJECT-TYPE
			SYNTAX GpioLogicLevel
			ACCESS read-write
			STATUS mandatory
			DESCRIPTION
				"The logic level of the general purpose port no. 6"
			::= { neceConfigurationEntry 23 }

		
		-- 1.3.6.1.4.1.3715.14.2.100.3.1.1.24
		neceConfigGpio6Description OBJECT-TYPE
			SYNTAX DisplayString (SIZE (0..31))
			ACCESS read-write
			STATUS mandatory
			DESCRIPTION
				"A description for the general purpose port no. 6"
			::= { neceConfigurationEntry 24 }

		
--  READONLY !!!
		-- 1.3.6.1.4.1.3715.14.2.100.3.1.1.25
		neceConfigGpio7Type OBJECT-TYPE
			SYNTAX GpioType
			ACCESS read-only
			STATUS mandatory
			DESCRIPTION
				"The type of the general purpose port no. 7"
			::= { neceConfigurationEntry 25 }

		
		-- 1.3.6.1.4.1.3715.14.2.100.3.1.1.26
		neceConfigGpio7Mode OBJECT-TYPE
			SYNTAX GpioMode
			ACCESS read-write
			STATUS mandatory
			DESCRIPTION
				"The mode of the general purpose port no. 7"
			::= { neceConfigurationEntry 26 }

		
		-- 1.3.6.1.4.1.3715.14.2.100.3.1.1.27
		neceConfigGpio7LogicLevel OBJECT-TYPE
			SYNTAX GpioLogicLevel
			ACCESS read-write
			STATUS mandatory
			DESCRIPTION
				"The logic level of the general purpose port no. 7"
			::= { neceConfigurationEntry 27 }

		
		-- 1.3.6.1.4.1.3715.14.2.100.3.1.1.28
		neceConfigGpio7Description OBJECT-TYPE
			SYNTAX DisplayString (SIZE (0..31))
			ACCESS read-write
			STATUS mandatory
			DESCRIPTION
				"A description for the general purpose port no. 7"
			::= { neceConfigurationEntry 28 }

		
--  READONLY !!!
		-- 1.3.6.1.4.1.3715.14.2.100.3.1.1.29
		neceConfigGpio8Type OBJECT-TYPE
			SYNTAX GpioType
			ACCESS read-only
			STATUS mandatory
			DESCRIPTION
				"The type of the general purpose port no. 8"
			::= { neceConfigurationEntry 29 }

		
		-- 1.3.6.1.4.1.3715.14.2.100.3.1.1.30
		neceConfigGpio8Mode OBJECT-TYPE
			SYNTAX GpioMode
			ACCESS read-write
			STATUS mandatory
			DESCRIPTION
				"The mode of the general purpose port no. 8"
			::= { neceConfigurationEntry 30 }

		
		-- 1.3.6.1.4.1.3715.14.2.100.3.1.1.31
		neceConfigGpio8LogicLevel OBJECT-TYPE
			SYNTAX GpioLogicLevel
			ACCESS read-write
			STATUS mandatory
			DESCRIPTION
				"The logic level of the general purpose port no. 8"
			::= { neceConfigurationEntry 31 }

		
		-- 1.3.6.1.4.1.3715.14.2.100.3.1.1.32
		neceConfigGpio8Description OBJECT-TYPE
			SYNTAX DisplayString (SIZE (0..31))
			ACCESS read-write
			STATUS mandatory
			DESCRIPTION
				"A description for the general purpose port no. 8"
			::= { neceConfigurationEntry 32 }

		
--  READONLY !!!
		-- 1.3.6.1.4.1.3715.14.2.100.3.1.1.33
		neceConfigGpio9Type OBJECT-TYPE
			SYNTAX GpioType
			ACCESS read-only
			STATUS mandatory
			DESCRIPTION
				"The type of the general purpose port no. 9"
			::= { neceConfigurationEntry 33 }

		
		-- 1.3.6.1.4.1.3715.14.2.100.3.1.1.34
		neceConfigGpio9Mode OBJECT-TYPE
			SYNTAX GpioMode
			ACCESS read-write
			STATUS mandatory
			DESCRIPTION
				"The mode of the general purpose port no. 9"
			::= { neceConfigurationEntry 34 }

		
		-- 1.3.6.1.4.1.3715.14.2.100.3.1.1.35
		neceConfigGpio9LogicLevel OBJECT-TYPE
			SYNTAX GpioLogicLevel
			ACCESS read-write
			STATUS mandatory
			DESCRIPTION
				"The logic level of the general purpose port no. 9"
			::= { neceConfigurationEntry 35 }

		
		-- 1.3.6.1.4.1.3715.14.2.100.3.1.1.36
		neceConfigGpio9Description OBJECT-TYPE
			SYNTAX DisplayString (SIZE (0..31))
			ACCESS read-write
			STATUS mandatory
			DESCRIPTION
				"A description for the general purpose port no. 9"
			::= { neceConfigurationEntry 36 }

		
--  READONLY !!!
		-- 1.3.6.1.4.1.3715.14.2.100.3.1.1.37
		neceConfigGpio10Type OBJECT-TYPE
			SYNTAX GpioType
			ACCESS read-only
			STATUS mandatory
			DESCRIPTION
				"The type of the general purpose port no. 10"
			::= { neceConfigurationEntry 37 }

		
		-- 1.3.6.1.4.1.3715.14.2.100.3.1.1.38
		neceConfigGpio10Mode OBJECT-TYPE
			SYNTAX GpioMode
			ACCESS read-write
			STATUS mandatory
			DESCRIPTION
				"The mode of the general purpose port no. 10"
			::= { neceConfigurationEntry 38 }

		
		-- 1.3.6.1.4.1.3715.14.2.100.3.1.1.39
		neceConfigGpio10LogicLevel OBJECT-TYPE
			SYNTAX GpioLogicLevel
			ACCESS read-write
			STATUS mandatory
			DESCRIPTION
				"The logic level of the general purpose port no. 10"
			::= { neceConfigurationEntry 39 }

		
		-- 1.3.6.1.4.1.3715.14.2.100.3.1.1.40
		neceConfigGpio10Description OBJECT-TYPE
			SYNTAX DisplayString (SIZE (0..31))
			ACCESS read-write
			STATUS mandatory
			DESCRIPTION
				"A description for the general purpose port no. 10"
			::= { neceConfigurationEntry 40 }

		
--  READONLY !!!
		-- 1.3.6.1.4.1.3715.14.2.100.3.1.1.41
		neceConfigGpio11Type OBJECT-TYPE
			SYNTAX GpioType
			ACCESS read-only
			STATUS mandatory
			DESCRIPTION
				"The type of the general purpose port no. 11"
			::= { neceConfigurationEntry 41 }

		
		-- 1.3.6.1.4.1.3715.14.2.100.3.1.1.42
		neceConfigGpio11Mode OBJECT-TYPE
			SYNTAX GpioMode
			ACCESS read-write
			STATUS mandatory
			DESCRIPTION
				"The mode of the general purpose port no. 11"
			::= { neceConfigurationEntry 42 }

		
		-- 1.3.6.1.4.1.3715.14.2.100.3.1.1.43
		neceConfigGpio11LogicLevel OBJECT-TYPE
			SYNTAX GpioLogicLevel
			ACCESS read-write
			STATUS mandatory
			DESCRIPTION
				"The logic level of the general purpose port no. 11"
			::= { neceConfigurationEntry 43 }

		
		-- 1.3.6.1.4.1.3715.14.2.100.3.1.1.44
		neceConfigGpio11Description OBJECT-TYPE
			SYNTAX DisplayString (SIZE (0..31))
			ACCESS read-write
			STATUS mandatory
			DESCRIPTION
				"A description for the general purpose port no. 11"
			::= { neceConfigurationEntry 44 }

		
--  READONLY !!!
		-- 1.3.6.1.4.1.3715.14.2.100.3.1.1.45
		neceConfigGpio12Type OBJECT-TYPE
			SYNTAX GpioType
			ACCESS read-only
			STATUS mandatory
			DESCRIPTION
				"The type of the general purpose port no. 12"
			::= { neceConfigurationEntry 45 }

		
		-- 1.3.6.1.4.1.3715.14.2.100.3.1.1.46
		neceConfigGpio12Mode OBJECT-TYPE
			SYNTAX GpioMode
			ACCESS read-write
			STATUS mandatory
			DESCRIPTION
				"The mode of the general purpose port no. 12"
			::= { neceConfigurationEntry 46 }

		
		-- 1.3.6.1.4.1.3715.14.2.100.3.1.1.47
		neceConfigGpio12LogicLevel OBJECT-TYPE
			SYNTAX GpioLogicLevel
			ACCESS read-write
			STATUS mandatory
			DESCRIPTION
				"The logic level of the general purpose port no. 12"
			::= { neceConfigurationEntry 47 }

		
		-- 1.3.6.1.4.1.3715.14.2.100.3.1.1.48
		neceConfigGpio12Description OBJECT-TYPE
			SYNTAX DisplayString (SIZE (0..31))
			ACCESS read-write
			STATUS mandatory
			DESCRIPTION
				"A description for the general purpose port no. 12"
			::= { neceConfigurationEntry 48 }

		
		-- 1.3.6.1.4.1.3715.14.2.100.3.1.1.49
		neceConfigNESlotWrite OBJECT-TYPE
			SYNTAX NESlotWriteValue
			ACCESS read-write
			STATUS mandatory
			DESCRIPTION
				"By writing this variable a slot can be assigned 
				for devices that dont support hardware slot detection.
				Reading '-1' means that the slot position is NOT writable."
			::= { neceConfigurationEntry 49 }

		
		-- 1.3.6.1.4.1.3715.14.2.100.3.1.1.50
		neceConfigIpAddress OBJECT-TYPE
			SYNTAX IpAddress
			ACCESS read-write
			STATUS mandatory
			DESCRIPTION
				"The ipaddress of the NEC.
				NOTE: The NECE executes a reset if this parameter gets changed"
			::= { neceConfigurationEntry 50 }

		
		-- 1.3.6.1.4.1.3715.14.2.100.3.1.1.51
		neceConfigNetmask OBJECT-TYPE
			SYNTAX IpAddress
			ACCESS read-write
			STATUS mandatory
			DESCRIPTION
				"The netmask of the NEC.
				NOTE: The NECE executes a reset if this parameter gets changed"
			::= { neceConfigurationEntry 51 }

		
		-- 1.3.6.1.4.1.3715.14.2.100.3.1.1.52
		neceConfigDefaultrouter OBJECT-TYPE
			SYNTAX IpAddress
			ACCESS read-write
			STATUS mandatory
			DESCRIPTION
				"The default router of the NEC.
				NOTE: The NECE executes a reset if this parameter gets changed"
			::= { neceConfigurationEntry 52 }

		
		-- 1.3.6.1.4.1.3715.14.2.100.3.1.1.53
		neceConfigTrapReceiver1HostIp OBJECT-TYPE
			SYNTAX IpAddress
			ACCESS read-write
			STATUS mandatory
			DESCRIPTION
				"The ipaddress of the host no.1 that should receive traps
				Address  0.0.0.0 disables the trap. Broad- or multicast addresses 
				are not allowed"
			::= { neceConfigurationEntry 53 }

		
		-- 1.3.6.1.4.1.3715.14.2.100.3.1.1.54
		neceConfigTrapReceiver1Community OBJECT-TYPE
			SYNTAX DisplayString (SIZE (4..31))
			ACCESS read-write
			STATUS mandatory
			DESCRIPTION
				"The community name used for traps to host no.1"
			::= { neceConfigurationEntry 54 }

		
		-- 1.3.6.1.4.1.3715.14.2.100.3.1.1.55
		neceConfigTrapReceiver2HostIp OBJECT-TYPE
			SYNTAX IpAddress
			ACCESS read-write
			STATUS mandatory
			DESCRIPTION
				"The ipaddress of the host no.2 that should receive traps
				Address  0.0.0.0 disables the trap. Broad- or multicast addresses 
				are not allowed"
			::= { neceConfigurationEntry 55 }

		
		-- 1.3.6.1.4.1.3715.14.2.100.3.1.1.56
		neceConfigTrapReceiver2to4Community OBJECT-TYPE
			SYNTAX DisplayString (SIZE (4..31))
			ACCESS read-write
			STATUS mandatory
			DESCRIPTION
				"The community name used for traps to hosts no.2 to no.4"
			::= { neceConfigurationEntry 56 }

		
		-- 1.3.6.1.4.1.3715.14.2.100.3.1.1.57
		neceConfigTrapReceiver3HostIp OBJECT-TYPE
			SYNTAX IpAddress
			ACCESS read-write
			STATUS mandatory
			DESCRIPTION
				"The ipaddress of the host no.3 that should receive traps
				Address  0.0.0.0 disables the trap. Broad- or multicast addresses 
				are not allowed
				NOTE: The community name 'neceConfigTrapReceiver2to4Community' is 
				used for this trap receiver no. 3"
			::= { neceConfigurationEntry 57 }

		
		-- 1.3.6.1.4.1.3715.14.2.100.3.1.1.58
		neceConfigTrapReceiver4HostIp OBJECT-TYPE
			SYNTAX IpAddress
			ACCESS read-write
			STATUS mandatory
			DESCRIPTION
				"The ipaddress of the host no.4 that should receive traps
				Address  0.0.0.0 disables the trap. Broad- or multicast addresses 
				are not allowed
				NOTE: The community name 'neceConfigTrapReceiver2to4Community' is 
				used for this trap receiver no. 4"
			::= { neceConfigurationEntry 58 }

		
		-- 1.3.6.1.4.1.3715.14.2.100.3.1.1.59
		neceConfigGetCommunity OBJECT-TYPE
			SYNTAX DisplayString (SIZE (0..15))
			ACCESS read-write
			STATUS mandatory
			DESCRIPTION
				"The community name that is allowed for GET requests
				NOTES: 
				- By writing 'neceConfigGetCommunity' AND 'neceConfigSetCommunity' 
				  to an empty string of size 0, the default community settings
				  are used."
			::= { neceConfigurationEntry 59 }

		
		-- 1.3.6.1.4.1.3715.14.2.100.3.1.1.60
		neceConfigSetCommunity OBJECT-TYPE
			SYNTAX DisplayString (SIZE (0..15))
			ACCESS read-write
			STATUS mandatory
			DESCRIPTION
				"The community name that is allowed for SET and GET requests
				NOTES: 
				- By writing 'neceConfigGetCommunity' AND 'neceConfigSetCommunity' 
				  to an empty string of size 0, the default community settings
				  are used."
			::= { neceConfigurationEntry 60 }

		
		-- 1.3.6.1.4.1.3715.14.2.100.3.1.1.61
		neceConfigTrapReceiverVerify OBJECT-TYPE
			SYNTAX TruthValue
			ACCESS read-write
			STATUS mandatory
			DESCRIPTION
				"If TRUE, the NECE verifies if the 'sysDescr' variable is readable on host 
				with ip-address 'neceConfigTrapVerifyReceiverIp' before sending new traps.
				NOTE: The NECE executes a reset if this parameter gets changed"
			::= { neceConfigurationEntry 61 }

		
		-- 1.3.6.1.4.1.3715.14.2.100.3.1.1.62
		neceConfigTrapVerifyReceiverIp OBJECT-TYPE
			SYNTAX IpAddress
			ACCESS read-write
			STATUS mandatory
			DESCRIPTION
				"The ipaddress of the host that should receive the 'sysDescr' verify request. 
				Broad- or multicast addresses are not allowed.
				!!! Only valid if neceConfigTrapReceiverVerify == true(1) !!!"
			::= { neceConfigurationEntry 62 }

		
		-- 1.3.6.1.4.1.3715.14.2.100.3.1.1.63
		neceConfigTrapVerifyTimeout OBJECT-TYPE
			SYNTAX TrapVerifyTimeoutValue
			ACCESS read-write
			STATUS mandatory
			DESCRIPTION
				"Timeout in seconds after which the NECE stops trying to verify 'sysDescr'.
				All pending traps are sent, although no verify response, after that timeout.
				!!! Only valid if neceConfigTrapReceiverVerify == true(1) !!!"
			::= { neceConfigurationEntry 63 }

		
		-- 1.3.6.1.4.1.3715.14.2.100.3.1.1.64
		neceConfigTrapAccumulationTime OBJECT-TYPE
			SYNTAX TrapAccumulationTimeValue
			ACCESS read-write
			STATUS mandatory
			DESCRIPTION
				"Time in seconds that the NECE waits before sending all pending traps.
				NOTE: There are two condition where the NECE sends its pending traps earlier
				ignoring this accumulation time (of course verifying first):
				1) The NECE's internal trap buffer is 3/4 full
				2) The NECE's SNMP agent is polled by a request from manager
				!!! Only valid if neceConfigTrapReceiverVerify == true(1) !!!"
			::= { neceConfigurationEntry 64 }

		
		-- 1.3.6.1.4.1.3715.14.2.100.3.1.1.65
		neceConfigCableWatchUsed OBJECT-TYPE
			SYNTAX TruthValue
			ACCESS read-write
			STATUS mandatory
			DESCRIPTION
				"If TRUE, the BKtel CABLEwatch network management system is to be used.
				The behaviour of the SNMP agent is a little bit different in both modes.
				See manual for details.
				NOTE: The NECE executes a reset if this parameter gets changed"
			::= { neceConfigurationEntry 65 }

		
		-- 1.3.6.1.4.1.3715.14.2.100.3.1.1.66
		neceConfigHmsTrapsCompliance OBJECT-TYPE
			SYNTAX HmsTrapsComplianceValue
			ACCESS read-write
			STATUS mandatory
			DESCRIPTION
				"Set the compliance mode of the SCTE HMS traps
				In earlier versions of NECE (<= Sw.Rel. 1.10) the trap compliance
				to the SCTE HMS MIBs was not fully given. See manual for details."
			::= { neceConfigurationEntry 66 }

		
		-- 1.3.6.1.4.1.3715.14.2.100.3.1.1.67
		neceConfigHmsNotificationsEnable OBJECT-TYPE
			SYNTAX TruthValue
			ACCESS read-write
			STATUS mandatory
			DESCRIPTION
				"With this control the user can disable all traps of type NOTIFY 
				and there entries in the SCTE HMS tree.
				NOTE: The NECE executes a reset if this parameter gets changed"
			::= { neceConfigurationEntry 67 }

		
		-- 1.3.6.1.4.1.3715.14.2.100.3.1.1.68
		neceConfigHfcInventoryFormat OBJECT-TYPE
			SYNTAX HfcInventoryFormatValue
			ACCESS read-write
			STATUS mandatory
			DESCRIPTION
				"Selects the supported format of the hfcInventoryFabricData (T-NOVA-HFC-INVENTORY-MIB)"
			::= { neceConfigurationEntry 68 }

		
		-- 1.3.6.1.4.1.3715.14.2.100.3.1.1.69
		neceConfigFactoryInternal OBJECT-TYPE
			SYNTAX TruthValue
			ACCESS read-only
			STATUS mandatory
			DESCRIPTION
				"Variable for factory use only, dont care."
			::= { neceConfigurationEntry 69 }

		
		-- 1.3.6.1.4.1.3715.14.2.100.4
		neceControl OBJECT IDENTIFIER ::= { nec 4 }

		
-- NEC control table
		-- 1.3.6.1.4.1.3715.14.2.100.4.1
		neceControlTable OBJECT-TYPE
			SYNTAX SEQUENCE OF NeceControlEntry
			ACCESS not-accessible
			STATUS mandatory
			::= { neceControl 1 }

		
-- Table row definition
		-- 1.3.6.1.4.1.3715.14.2.100.4.1.1
		neceControlEntry OBJECT-TYPE
			SYNTAX NeceControlEntry
			ACCESS not-accessible
			STATUS mandatory
			DESCRIPTION
				"Alarms for a module."
			INDEX { neceNESlot }
			::= { neceControlTable 1 }

		
		NeceControlEntry ::=
			SEQUENCE { 
				neceControlReset
					TruthValue
			 }

		-- 1.3.6.1.4.1.3715.14.2.100.4.1.1.1
		neceControlReset OBJECT-TYPE
			SYNTAX TruthValue
			ACCESS read-write
			STATUS mandatory
			DESCRIPTION
				"Reset the module."
			::= { neceControlEntry 1 }

		
		-- 1.3.6.1.4.1.3715.14.2.100.5
		neceMeasuringValues OBJECT IDENTIFIER ::= { nec 5 }

		
-- NEC measurement values table
		-- 1.3.6.1.4.1.3715.14.2.100.5.1
		neceMeasuringValuesTable OBJECT-TYPE
			SYNTAX SEQUENCE OF NeceMeasuringValuesEntry
			ACCESS not-accessible
			STATUS mandatory
			::= { neceMeasuringValues 1 }

		
-- Table row definition
		-- 1.3.6.1.4.1.3715.14.2.100.5.1.1
		neceMeasuringValuesEntry OBJECT-TYPE
			SYNTAX NeceMeasuringValuesEntry
			ACCESS not-accessible
			STATUS mandatory
			DESCRIPTION
				"Common-Values for a module."
			INDEX { neceNESlot }
			::= { neceMeasuringValuesTable 1 }

		
		NeceMeasuringValuesEntry ::=
			SEQUENCE { 
				neceTemperatureMin
					INTEGER,
				neceTemperatureStartGreen
					INTEGER,
				neceTemperatureValue
					INTEGER,
				neceTemperatureEndGreen
					INTEGER,
				neceTemperatureMax
					INTEGER
			 }

		-- 1.3.6.1.4.1.3715.14.2.100.5.1.1.1
		neceTemperatureMin OBJECT-TYPE
			SYNTAX INTEGER
			ACCESS read-only
			STATUS mandatory
			DESCRIPTION
				"Temperature minimum value in steps of 0,1°C."
			::= { neceMeasuringValuesEntry 1 }

		
		-- 1.3.6.1.4.1.3715.14.2.100.5.1.1.2
		neceTemperatureStartGreen OBJECT-TYPE
			SYNTAX INTEGER
			ACCESS read-only
			STATUS mandatory
			DESCRIPTION
				"Temperature start green range in steps of 0,1°C."
			::= { neceMeasuringValuesEntry 2 }

		
		-- 1.3.6.1.4.1.3715.14.2.100.5.1.1.3
		neceTemperatureValue OBJECT-TYPE
			SYNTAX INTEGER
			ACCESS read-only
			STATUS mandatory
			DESCRIPTION
				"Temperature in steps of 0,1°C."
			::= { neceMeasuringValuesEntry 3 }

		
		-- 1.3.6.1.4.1.3715.14.2.100.5.1.1.4
		neceTemperatureEndGreen OBJECT-TYPE
			SYNTAX INTEGER
			ACCESS read-only
			STATUS mandatory
			DESCRIPTION
				"Temperature end green range in steps of 0,1°C."
			::= { neceMeasuringValuesEntry 4 }

		
		-- 1.3.6.1.4.1.3715.14.2.100.5.1.1.5
		neceTemperatureMax OBJECT-TYPE
			SYNTAX INTEGER
			ACCESS read-only
			STATUS mandatory
			DESCRIPTION
				"Temperature maximum value in steps of 0,1°C."
			::= { neceMeasuringValuesEntry 5 }

		
		-- 1.3.6.1.4.1.3715.14.2.100.6
		neceDisplay OBJECT IDENTIFIER ::= { nec 6 }

		
-- NEC display table
		-- 1.3.6.1.4.1.3715.14.2.100.6.1
		neceDisplayTable OBJECT-TYPE
			SYNTAX SEQUENCE OF NeceDisplayEntry
			ACCESS not-accessible
			STATUS mandatory
			::= { neceDisplay 1 }

		
-- Table row definition
		-- 1.3.6.1.4.1.3715.14.2.100.6.1.1
		neceDisplayEntry OBJECT-TYPE
			SYNTAX NeceDisplayEntry
			ACCESS not-accessible
			STATUS mandatory
			INDEX { neceNESlot }
			::= { neceDisplayTable 1 }

		
		NeceDisplayEntry ::=
			SEQUENCE { 
				neceDisplayTrapsSent
					INTEGER,
				neceDisplayTrapsDiscarded
					INTEGER
			 }

		-- 1.3.6.1.4.1.3715.14.2.100.6.1.1.1
		neceDisplayTrapsSent OBJECT-TYPE
			SYNTAX INTEGER
			ACCESS read-only
			STATUS mandatory
			DESCRIPTION
				"Number of traps that the NECE has sent"
			::= { neceDisplayEntry 1 }

		
		-- 1.3.6.1.4.1.3715.14.2.100.6.1.1.2
		neceDisplayTrapsDiscarded OBJECT-TYPE
			SYNTAX INTEGER
			ACCESS read-only
			STATUS mandatory
			DESCRIPTION
				"Number of traps that the NECE has discarded.
				Discarded traps occur because of trap buffer overflow or because they have
				not been acknowledged by 'neceConfigTrapVerifyReceiverIp' before sending.
				Note that unacknowledged traps that are sent after a 'neceConfigTrapVerifyTimeout'
				are also counted as discarded."
			::= { neceDisplayEntry 2 }

		
	
	END

--
-- TELESTE-HDONE-MIB.mib
--
