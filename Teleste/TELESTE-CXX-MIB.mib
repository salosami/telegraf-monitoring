--
-- TELESTE-CXX-MIB.mib
-- MIB generated by MG-SOFT Visual MIB Builder 2013 (64-bit) Version 9.0  Build 720
-- Thursday, October 24, 2013 at 14:57:46
--

-- ****************************************************************************
-- Copyright (c) 2005-2013 by:
-- 
-- Teleste Corporation
-- Telestenkatu 1
-- FIN-20660 Littoinen, Finland
-- tel. +358 2 2605 611
-- url: http://www.teleste.com
-- 
-- Description: CXX module definitions 
-- 
-- Revision History:
-- -----------------
-- 4, 24.10.2013 Sami Halen
-- - renamed cxe85x to cxeNode
-- - added cxe940
-- 
-- 3, 14.9.2012 Sami Halen
-- - added cxe851
-- 
-- 2, 15.3.2012 Sami Halen
-- - renamed cxe850->cxe85x, added cxe850 & cxe852
-- 
-- 1, 16.12.2009 Rainer Salminen and Sami Salo
-- - first official version
-- 
-- ****************************************************************************

	TELESTE-CXX-MIB DEFINITIONS ::= BEGIN
 
		IMPORTS
			cxx			
				FROM TELESTE-ROOT-MIB;
	
	
	
--
-- Node definitions
--
	
-- Object identifier for CXE nodes
		-- 1.3.6.1.4.1.3715.18.850
		cxeNode OBJECT IDENTIFIER ::= { cxx 850 }

		
		-- 1.3.6.1.4.1.3715.18.851
		cxe851 OBJECT IDENTIFIER ::= { cxx 851 }

		
		-- 1.3.6.1.4.1.3715.18.852
		cxe852 OBJECT IDENTIFIER ::= { cxx 852 }

		
		-- 1.3.6.1.4.1.3715.18.940
		cxe940 OBJECT IDENTIFIER ::= { cxx 940 }

		
	
	END

--
-- TELESTE-CXX-MIB.mib
--
