--
-- TELESTE-FUNCTIONAL-PACKET-STATISTICS-MIB.mib
-- MIB generated by MG-SOFT Visual MIB Builder 2013 (64-bit) Version 9.0  Build 760
-- Monday, December 08, 2014 at 08:15:09
--

-- ****************************************************************************
-- Copyright (c) 2003-2014 by:
-- 
-- Teleste Corporation
-- Seponkatu 1
-- FIN-20660 Littoinen, Finland
-- tel. +358 2 2605 611
-- url: http://www.teleste.com
-- 
-- Module Name: TELESTE-FUNCTIONAL-PACKET-STATISTICS-MIB
-- 
-- Description: MIB module describing objects for a interface transferring packets.
-- 
-- Revision History:
-- -----------------
-- 1, 8.12.2014, Sami Kuusisto
-- - Initial version
-- 
-- ****************************************************************************

	TELESTE-FUNCTIONAL-PACKET-STATISTICS-MIB DEFINITIONS ::= BEGIN
 
		IMPORTS
			OBJECT-TYPE			
				FROM RFC-1212			
			Counter			
				FROM RFC1155-SMI			
			functionalModuleId			
				FROM TELESTE-FUNCTIONAL-MODULE-MIB			
			functional			
				FROM TELESTE-ROOT-MIB;
	
	
	
--
-- Node definitions
--
	
		-- 1.3.6.1.4.1.3715.100.97
		packetStatistics OBJECT IDENTIFIER ::= { functional 97 }

		
		-- 1.3.6.1.4.1.3715.100.97.3
		packetStatisticsTable OBJECT-TYPE
			SYNTAX SEQUENCE OF PacketStatisticsEntry
			ACCESS not-accessible
			STATUS mandatory
			::= { packetStatistics 3 }

		
		-- 1.3.6.1.4.1.3715.100.97.3.1
		packetStatisticsEntry OBJECT-TYPE
			SYNTAX PacketStatisticsEntry
			ACCESS not-accessible
			STATUS mandatory
			INDEX { functionalModuleId }
			::= { packetStatisticsTable 1 }

		
		PacketStatisticsEntry ::=
			SEQUENCE { 
				packetStatisticsReceived
					Counter,
				packetStatisticsBad
					Counter,
				packetStatisticsSent
					Counter,
				packetStatisticsReset
					INTEGER
			 }

		-- 1.3.6.1.4.1.3715.100.97.3.1.1
		packetStatisticsReceived OBJECT-TYPE
			SYNTAX Counter
			ACCESS read-only
			STATUS mandatory
			DESCRIPTION
				"Number of received packets."
			::= { packetStatisticsEntry 1 }

		
		-- 1.3.6.1.4.1.3715.100.97.3.1.2
		packetStatisticsBad OBJECT-TYPE
			SYNTAX Counter
			ACCESS read-only
			STATUS mandatory
			DESCRIPTION
				"Number of received packets declared as bad."
			::= { packetStatisticsEntry 2 }

		
		-- 1.3.6.1.4.1.3715.100.97.3.1.3
		packetStatisticsSent OBJECT-TYPE
			SYNTAX Counter
			ACCESS read-only
			STATUS mandatory
			DESCRIPTION
				"Number of sent packets."
			::= { packetStatisticsEntry 3 }

		
		-- 1.3.6.1.4.1.3715.100.97.3.1.4
		packetStatisticsReset OBJECT-TYPE
			SYNTAX INTEGER
			ACCESS read-write
			STATUS mandatory
			DESCRIPTION
				"Write only variable for resetting the modem packet
				statistics counters. A get operation returns always value 1."
			::= { packetStatisticsEntry 4 }

		
	
	END

--
-- TELESTE-FUNCTIONAL-PACKET-STATISTICS-MIB.mib
--
