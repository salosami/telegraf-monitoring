--
-- TELESTE-FUNCTIONAL-AMPLIFIER-RETURN-PATH-MIB.mib
-- MIB generated by MG-SOFT Visual MIB Builder 2024 (64-bit) Version 17.00  Build 1700
-- Tuesday, September 10, 2024 at 07:47:30
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-AMPLIFIER-RETURN-PATH-MIB
-- 
-- Description:   MIB module describing Teleste functional amplifier return path interface specific objects
-- 
-- Revision history:
-- -----------------
-- 3, 10.9.2024, Sami Kuusisto
-- - Added new enum rffRestart(5) to amplifierReturnPathRffControl.
-- 
-- 2, 12.4.2023, Sami Kuusisto
-- - Added amplifierReturnPathRffControl, amplifierReturnPathAutomaticBoostValuesUpdateControl and amplifierReturnPathBoostValuesUpdateNow.
-- 
-- 1, 11.3.2014, Sami Kuusisto
-- - Initial version.
-- 
-- ****************************************************************************
-- 

	TELESTE-FUNCTIONAL-AMPLIFIER-RETURN-PATH-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.51
		amplifierReturnPath OBJECT IDENTIFIER ::= { functional 51 }

		
		-- 1.3.6.1.4.1.3715.100.51.1
		amplifierReturnPathRffControl OBJECT-TYPE
			SYNTAX INTEGER
				{
				rffEnabled(1),
				rffDisabled(2),
				rffUnknown(3),
				rffNA(4),
				rffRestart(5)
				}
			ACCESS read-write
			STATUS mandatory
			DESCRIPTION
				"Enable/Disable Return Follows Forward (RFF: old name iRPC (intelligent Return Path Control)).
				1: Enabled, 
				2: Disabled, 
				3: Unknown, 
				4: N/A,
				5: Restart"
			::= { amplifierReturnPath 1 }

		
		-- 1.3.6.1.4.1.3715.100.51.2
		amplifierReturnPathAutomaticBoostValuesUpdateControl OBJECT-TYPE
			SYNTAX INTEGER
				{
				automaticBoostValuesUpdateControlEnabled(1),
				automaticBoostValuesUpdateControlDisabled(2),
				automaticBoostValuesUpdateControlUnknown(3),
				automaticBoostValuesUpdateControlNA(4)
				}
			ACCESS read-write
			STATUS mandatory
			DESCRIPTION
				"Enable/Disable automatic return path boost values updates based on changes on ReturnPath gain and slope values.
				
				1: Enabled, 2: Disabled, 3: Unknown, 4: N/A.
				
				Gain and slope boost values are used by AutoAlign. See iso(1).org(3).dod(6).internet(1).private(4).enterprises(1).teleste(3715).functional(100).automaticAlignmentButton(94).
				GainBoost:  teleste(3715).functional(100).automaticAlignmentButton(94).automaticAlignmentOptionsTable(4).automaticAlignmentOptionsEntry(1).automaticAlignmentOptionValue(4).512
				SlopeBoost: teleste(3715).functional(100).automaticAlignmentButton(94).automaticAlignmentOptionsTable(4).automaticAlignmentOptionsEntry(1).automaticAlignmentOptionValue2(6).512"
			::= { amplifierReturnPath 2 }

		
		-- 1.3.6.1.4.1.3715.100.51.3
		amplifierReturnPathBoostValuesUpdateNow OBJECT-TYPE
			SYNTAX INTEGER
				{
				boostValuesUpdateNow(1),
				boostValuesUpdateNowReadAlwaysValue(2)
				}
			ACCESS read-write
			STATUS mandatory
			DESCRIPTION
				"Update return path boost values now (based on difference between gain and slope values calculated by AutoAlign (using current boost values) and current return path gain and slope values).
				
				1: Update know. 
				(Read returns always 2).
				
				Current ReturnPath gain and slope values are here: iso(1).org(3).dod(6).internet(1).private(4).enterprises(1).teleste(3715).functional(100).levelControl(71).levelControlTable(1).levelControlEntry(1).levelControlValue(1).
				
				Gain and slope boost values are used by AutoAlign. See iso(1).org(3).dod(6).internet(1).private(4).enterprises(1).teleste(3715).functional(100).automaticAlignmentButton(94).
				GainBoost:  teleste(3715).functional(100).automaticAlignmentButton(94).automaticAlignmentOptionsTable(4).automaticAlignmentOptionsEntry(1).automaticAlignmentOptionValue(4).512.
				SlopeBoost: teleste(3715).functional(100).automaticAlignmentButton(94).automaticAlignmentOptionsTable(4).automaticAlignmentOptionsEntry(1).automaticAlignmentOptionValue2(6).512."
			::= { amplifierReturnPath 3 }

		
	
	END

--
-- TELESTE-FUNCTIONAL-AMPLIFIER-RETURN-PATH-MIB.mib
--
