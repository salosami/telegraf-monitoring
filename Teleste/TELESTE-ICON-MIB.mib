--
-- TELESTE-ICON-MIB.mib
-- MIB generated by MG-SOFT Visual MIB Builder 2024 (64-bit) Version 17.00  Build 1700
-- Tuesday, September 03, 2024 at 12:56:13
--

-- ****************************************************************************
-- Copyright (c) 2003-2017 by:
-- 
-- Teleste Corporation
-- Seponkatu 1
-- FIN-20660 Littoinen, Finland
-- tel. +358 2 2605 611
-- url: http://www.teleste.com
-- 
-- Module Name:   TELESTE-ICON-MIB
-- 
-- Description:   MIB module describing Teleste ICON series specific objects
-- 
-- Revision history:
-- -----------------
-- 12, 3.9.2024, Sami Kuusisto
-- - Added icon3101 and icon4301 sysOIDs and copied icon3100/icon4300 tree as icon3101/icon4301 tree.
-- 
-- 11, 4.3.2024, Sami Kuusisto
-- - Added icon4300AuxControl.
-- 
-- 10, 13.2.2024, Sami Kuusisto
-- - Added icon3100hayStackControl.
-- 
-- 9, 29.11.2022, Sami Kuusisto
-- - Added icon4300MainOutputTcp, icon4300Aux2OutputTcp and icon4300Aux2OutputTcp.
-- 
-- 8, 13.6.2022, Sami Kuusisto
-- - Added icon3100slopeMode and icon4300slopeMode.
-- 
-- 7, 15.2.2021, Sami Kuusisto
-- - Added icon4300 sysOID.
-- 
-- 6, 9.9.2020, Sami Kuusisto
-- - Added diplexerSelection to ICON3100.
-- 
-- 5, 26.05.2020, Sami Kuusisto
-- - Added icon3100 sysOID.
-- 
-- 4, 28.11.2019, Sami Kuusisto
-- - Added measuredPower.
-- 
-- 3, 18.9.2018, Sami Kuusisto
-- - Renamed icon9000 to icon7900.
-- 
-- 2, 1.12.2017, Sami Kuusisto
-- - Added forwardPathTestPoint12/34Control.
-- 
-- 1, 7.11.2017, Sami Kuusisto
-- - Initial version.
-- 
-- 
-- ****************************************************************************
-- 

	TELESTE-ICON-MIB DEFINITIONS ::= BEGIN
 
		IMPORTS
			OBJECT-TYPE			
				FROM RFC-1212			
			icon			
				FROM TELESTE-ROOT-MIB;
	
	
	
--
-- Node definitions
--
	
-- ICON series - ICON3100 - Intelligent 1.8 GHz line extender with 1G0 slope mode.
		-- 1.3.6.1.4.1.3715.20.3100
		icon3100 OBJECT IDENTIFIER ::= { icon 3100 }

		
		-- 1.3.6.1.4.1.3715.20.3100.1
		icon3100-generations OBJECT IDENTIFIER ::= { icon3100 1 }

		
		-- 1.3.6.1.4.1.3715.20.3100.2
		diplexerSelection OBJECT-TYPE
			SYNTAX INTEGER
				{
				diplexerSelectionDiplexers1(1),
				diplexerSelectionDiplexers2(2)
				}
			ACCESS read-write
			STATUS mandatory
			DESCRIPTION
				"Select used diplexers and return slope plug.
				1: Diplexers 1 and return slope plug 1.
				2: Diplexers 2 and return slope plug 2."
			::= { icon3100 2 }

		
		-- 1.3.6.1.4.1.3715.20.3100.3
		icon3100slopeMode OBJECT-TYPE
			SYNTAX INTEGER
				{
				icon3100SlopeMode1G0(10),
				icon3100SlopeMode1G8(18)
				}
			ACCESS read-write
			STATUS mandatory
			DESCRIPTION
				"ICON3100 slope mode.
				10: 1.0 GHz
				18: 1.8 GHz"
			::= { icon3100 3 }

		
		-- 1.3.6.1.4.1.3715.20.3100.4
		icon3100hayStackControl OBJECT-TYPE
			SYNTAX INTEGER
				{
				haystackEnabled(1),
				haystackDisabled(2),
				haystackNoChange(3)
				}
			ACCESS read-write
			STATUS mandatory
			DESCRIPTION
				"HayStack control. 
				1: Enable haystack correction
				2: No haystack correction in use
				3: No change (used by AutoAlign internally temporarily): do not set this"
			::= { icon3100 4 }

		
-- ICON series - ICON3101 - Intelligent 1.8 GHz line extender with 1G2 slope mode.
		-- 1.3.6.1.4.1.3715.20.3101
		icon3101 OBJECT IDENTIFIER ::= { icon 3101 }

		
		-- 1.3.6.1.4.1.3715.20.3101.1
		icon3101-generations OBJECT IDENTIFIER ::= { icon3101 1 }

		
		-- 1.3.6.1.4.1.3715.20.3101.2
		icon3101diplexerSelection OBJECT-TYPE
			SYNTAX INTEGER
				{
				diplexerSelectionDiplexers1(1),
				diplexerSelectionDiplexers2(2)
				}
			ACCESS read-write
			STATUS mandatory
			DESCRIPTION
				"Select used diplexers and return slope plug.
				1: Diplexers 1 and return slope plug 1.
				2: Diplexers 2 and return slope plug 2."
			::= { icon3101 2 }

		
		-- 1.3.6.1.4.1.3715.20.3101.3
		icon3101slopeMode OBJECT-TYPE
			SYNTAX INTEGER
				{
				icon3101SlopeMode1G2(12),
				icon3101SlopeMode1G8(18)
				}
			ACCESS read-write
			STATUS mandatory
			DESCRIPTION
				"ICON3101 slope mode.
				12: 1.2 GHz
				18: 1.8 GHz"
			::= { icon3101 3 }

		
		-- 1.3.6.1.4.1.3715.20.3101.4
		icon3101hayStackControl OBJECT-TYPE
			SYNTAX INTEGER
				{
				haystackEnabled(1),
				haystackDisabled(2),
				haystackNoChange(3)
				}
			ACCESS read-write
			STATUS mandatory
			DESCRIPTION
				"HayStack control. 
				1: Enable haystack correction
				2: No haystack correction in use
				3: No change (used by AutoAlign internally temporarily): do not set this"
			::= { icon3101 4 }

		
-- ICON series - ICON4300 - Intelligent 1.8 GHz system amplifier with 1G0 slope mode.
		-- 1.3.6.1.4.1.3715.20.4300
		icon4300 OBJECT IDENTIFIER ::= { icon 4300 }

		
		-- 1.3.6.1.4.1.3715.20.4300.1
		icon4300-generations OBJECT IDENTIFIER ::= { icon4300 1 }

		
		-- 1.3.6.1.4.1.3715.20.4300.3
		icon4300SlopeMode OBJECT-TYPE
			SYNTAX INTEGER
				{
				icon4300SlopeMode1G0(10),
				icon4300SlopeMode1G8(18)
				}
			ACCESS read-write
			STATUS mandatory
			DESCRIPTION
				"ICON4300 slope mode.
				10: 1.0 GHz
				18: 1.8 GHz"
			::= { icon4300 3 }

		
		-- 1.3.6.1.4.1.3715.20.4300.4
		icon4300MainOutputTcp OBJECT-TYPE
			SYNTAX INTEGER
			ACCESS read-only
			STATUS mandatory
			DESCRIPTION
				"Measured main output TCP.
				Unit 0.01 dBµV."
			::= { icon4300 4 }

		
		-- 1.3.6.1.4.1.3715.20.4300.5
		icon4300Aux1OutputTcp OBJECT-TYPE
			SYNTAX INTEGER
			ACCESS read-only
			STATUS mandatory
			DESCRIPTION
				"Calculated (based on measured main output TCP + aux 1 vs. main offset) aux 1 output TCP.
				Unit 0.01 dBµV."
			::= { icon4300 5 }

		
		-- 1.3.6.1.4.1.3715.20.4300.6
		icon4300Aux2OutputTcp OBJECT-TYPE
			SYNTAX INTEGER
			ACCESS read-only
			STATUS mandatory
			DESCRIPTION
				"Calculated (based on measured main output TCP + aux 2 vs. main offset) aux 2 output TCP.
				Unit 0.01 dBµV."
			::= { icon4300 6 }

		
		-- 1.3.6.1.4.1.3715.20.4300.7
		icon4300AuxControl OBJECT-TYPE
			SYNTAX INTEGER
				{
				icon4300AuxControlMainOnly(1),
				icon4300AuxControlMainAndAux1(3),
				icon4300AuxControlMainAndAux2(5),
				icon4300AuxControlMainAux1AndAux2(7)
				}
			ACCESS read-write
			STATUS mandatory
			DESCRIPTION
				"Main, aux1 and aux 2 output status.
				Aux 1 and aux 2 control.
				
				1: Only main output is active (main is always active).
				3: Main and aux 1 is active
				5: Main and aux 2 is active
				7: Main, aux 1 and aux 2 active"
			::= { icon4300 7 }

		
-- ICON series - ICON4301 - Intelligent 1.8 GHz system amplifier with 1G2 slope mode.
		-- 1.3.6.1.4.1.3715.20.4301
		icon4301 OBJECT IDENTIFIER ::= { icon 4301 }

		
		-- 1.3.6.1.4.1.3715.20.4301.1
		icon4301-generations OBJECT IDENTIFIER ::= { icon4301 1 }

		
		-- 1.3.6.1.4.1.3715.20.4301.2
		icon4301SlopeMode OBJECT-TYPE
			SYNTAX INTEGER
				{
				icon4301SlopeMode1G2(12),
				icon4301SlopeMode1G8(18)
				}
			ACCESS read-write
			STATUS mandatory
			DESCRIPTION
				"ICON4301 slope mode.
				12: 1.2 GHz
				18: 1.8 GHz"
			::= { icon4301 2 }

		
		-- 1.3.6.1.4.1.3715.20.4301.3
		icon4301MainOutputTcp OBJECT-TYPE
			SYNTAX INTEGER
			ACCESS read-only
			STATUS mandatory
			DESCRIPTION
				"Measured main output TCP.
				Unit 0.01 dBµV."
			::= { icon4301 3 }

		
		-- 1.3.6.1.4.1.3715.20.4301.4
		icon4301Aux1OutputTcp OBJECT-TYPE
			SYNTAX INTEGER
			ACCESS read-only
			STATUS mandatory
			DESCRIPTION
				"Calculated (based on measured main output TCP + aux 1 vs. main offset) aux 1 output TCP.
				Unit 0.01 dBµV."
			::= { icon4301 4 }

		
		-- 1.3.6.1.4.1.3715.20.4301.5
		icon4301Aux2OutputTcp OBJECT-TYPE
			SYNTAX INTEGER
			ACCESS read-only
			STATUS mandatory
			DESCRIPTION
				"Calculated (based on measured main output TCP + aux 2 vs. main offset) aux 2 output TCP.
				Unit 0.01 dBµV."
			::= { icon4301 5 }

		
		-- 1.3.6.1.4.1.3715.20.4301.6
		icon4301AuxControl OBJECT-TYPE
			SYNTAX INTEGER
				{
				icon4300AuxControlMainOnly(1),
				icon4300AuxControlMainAndAux1(3),
				icon4300AuxControlMainAndAux2(5),
				icon4300AuxControlMainAux1AndAux2(7)
				}
			ACCESS read-write
			STATUS mandatory
			DESCRIPTION
				"Main, aux1 and aux 2 output status.
				Aux 1 and aux 2 control.
				
				1: Only main output is active (main is always active).
				3: Main and aux 1 is active
				5: Main and aux 2 is active
				7: Main, aux 1 and aux 2 active"
			::= { icon4301 6 }

		
-- ICON series - ICON7900 - Intelligent 1.2 GHz fibre optic RF tray with RPD option to ICON9000 housing
		-- 1.3.6.1.4.1.3715.20.7900
		icon7900 OBJECT IDENTIFIER ::= { icon 7900 }

		
		-- 1.3.6.1.4.1.3715.20.7900.1
		forwardPathTestPoint12Control OBJECT-TYPE
			SYNTAX INTEGER
				{
				testPoint12Automatic(1),
				testPoint12Out1(2),
				testPoint12Out2(3)
				}
			ACCESS read-write
			STATUS mandatory
			DESCRIPTION
				"Forward path test point 1-2 control.
				1: Automatic
				2: Output 1
				3: Output 2"
			::= { icon7900 1 }

		
		-- 1.3.6.1.4.1.3715.20.7900.2
		forwardPathTestPoint34Control OBJECT-TYPE
			SYNTAX INTEGER
				{
				testPoint34Automatic(1),
				testPoint12Out3(4),
				testPoint34Out4(5)
				}
			ACCESS read-write
			STATUS mandatory
			DESCRIPTION
				"Forward path test point 3-4 control.
				1: Automatic
				4: Output 3
				5: Output 4"
			::= { icon7900 2 }

		
		-- 1.3.6.1.4.1.3715.20.7900.3
		measuredPower OBJECT-TYPE
			SYNTAX INTEGER
			ACCESS read-only
			STATUS mandatory
			DESCRIPTION
				"Measured total power.
				Unit 0.01 W."
			::= { icon7900 3 }

		
	
	END

--
-- TELESTE-ICON-MIB.mib
--
