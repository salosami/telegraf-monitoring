--
-- TELESTE-FUNCTIONAL-OPTICAL-FORWARD-RECEIVER-MIB.mib
-- MIB generated by MG-SOFT Visual MIB Builder 2013 (64-bit) Version 9.0  Build 760
-- Thursday, March 27, 2014 at 15:01:50
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-OPTICAL-FORWARD-RECEIVER-MIB
-- 
-- Description:   MIB module describing Teleste functional optical forward receiver interface specific objects
-- 
-- Revision history:
-- -----------------
-- 5, 27.3.2014, Sami Kuusisto
-- - Fixed opticalForwardReceiverControl|Status descriptions.
-- 
-- 4, 17.3.2014, Sami Kuusisto
-- - Restored opticalForwardReceiverAlarmLimitSet
-- 
-- 3, 14.3.2014, Sami Kuusisto
-- - Renamed opticalForwardReceiverEnable to opticalForwardReceiverControl.
-- 
-- 2, 14.3.2014, Sami Kuusisto
-- - removed opticalForwardReceiverAlarmLimitDistance and opticalForwardReceiverAlarmLimitSet (they are available at TRANSPONDER-SET-BUTTON-MIB).
-- 
-- 1, 11.3.2014, Sami Kuusisto
-- - Initial version.
-- 
-- ****************************************************************************
-- 

	TELESTE-FUNCTIONAL-OPTICAL-FORWARD-RECEIVER-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.47
		opticalForwardReceiver OBJECT IDENTIFIER ::= { functional 47 }

		
		-- 1.3.6.1.4.1.3715.100.47.1
		opticalForwardReceiverTable OBJECT-TYPE
			SYNTAX SEQUENCE OF OpticalForwardReceiverEntry
			ACCESS not-accessible
			STATUS mandatory
			DESCRIPTION
				"A table of optical receiver control entries."
			::= { opticalForwardReceiver 1 }

		
		-- 1.3.6.1.4.1.3715.100.47.1.1
		opticalForwardReceiverEntry OBJECT-TYPE
			SYNTAX OpticalForwardReceiverEntry
			ACCESS not-accessible
			STATUS mandatory
			INDEX { functionalModuleId }
			::= { opticalForwardReceiverTable 1 }

		
		OpticalForwardReceiverEntry ::=
			SEQUENCE { 
				opticalForwardReceiverInputPower
					INTEGER,
				opticalForwardReceiverStatus
					INTEGER,
				opticalForwardReceiverControl
					INTEGER,
				opticalForwardReceiverReferenceLevel
					INTEGER,
				opticalForwardReceiverOlcOffset
					INTEGER,
				opticalForwardReceiverAlarmLimitSet
					INTEGER
			 }

		-- 1.3.6.1.4.1.3715.100.47.1.1.1
		opticalForwardReceiverInputPower OBJECT-TYPE
			SYNTAX INTEGER
			ACCESS read-only
			STATUS mandatory
			DESCRIPTION
				"Optical input power value. Unit 0.01 dBm.
				This object has an entry in the propertyTable."
			::= { opticalForwardReceiverEntry 1 }

		
		-- 1.3.6.1.4.1.3715.100.47.1.1.2
		opticalForwardReceiverStatus OBJECT-TYPE
			SYNTAX INTEGER
				{
				on(1),
				off(2)
				}
			ACCESS read-only
			STATUS mandatory
			DESCRIPTION
				"Current optical receiver status:
				1 = receiver enabled/on
				2 = receiver disabled/off
				"
			::= { opticalForwardReceiverEntry 2 }

		
		-- 1.3.6.1.4.1.3715.100.47.1.1.3
		opticalForwardReceiverControl OBJECT-TYPE
			SYNTAX INTEGER
				{
				rxEnabled(1),
				rxDisabled(2)
				}
			ACCESS read-write
			STATUS mandatory
			DESCRIPTION
				"Optical receiver control:
				1 = receiver is enabled/on
				2 = receiver is disabled/off"
			::= { opticalForwardReceiverEntry 3 }

		
		-- 1.3.6.1.4.1.3715.100.47.1.1.4
		opticalForwardReceiverReferenceLevel OBJECT-TYPE
			SYNTAX INTEGER
			ACCESS read-write
			STATUS mandatory
			DESCRIPTION
				"Optical receiver reference level. Unit 0.01 dBm."
			::= { opticalForwardReceiverEntry 4 }

		
		-- 1.3.6.1.4.1.3715.100.47.1.1.5
		opticalForwardReceiverOlcOffset OBJECT-TYPE
			SYNTAX INTEGER
			ACCESS read-write
			STATUS mandatory
			DESCRIPTION
				"OLC (Optical Level Control) offset. 
				Unit 0.01 dB."
			::= { opticalForwardReceiverEntry 5 }

		
		-- 1.3.6.1.4.1.3715.100.47.1.1.6
		opticalForwardReceiverAlarmLimitSet OBJECT-TYPE
			SYNTAX INTEGER
				{
				opticalForwardReceiverAlarmLimitSetLimits(1),
				opticalForwardReceiverAlarmLimitSetRO(2)
				}
			ACCESS read-write
			STATUS mandatory
			DESCRIPTION
				"Set alarm limits to distance ±X dB (transponderSetButtonOptionValue) from 
				current value (opticalForwardReceiverInputPower).
				
				1: Set limit.
				2: Reply when reading."
			::= { opticalForwardReceiverEntry 6 }

		
	
	END

--
-- TELESTE-FUNCTIONAL-OPTICAL-FORWARD-RECEIVER-MIB.mib
--
