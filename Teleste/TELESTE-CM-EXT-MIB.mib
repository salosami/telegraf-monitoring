--
-- TELESTE-CM-EXT-MIB.mib
-- MIB generated by MG-SOFT Visual MIB Builder 2021 (64-bit) Version 15.00  Build 1510
-- Tuesday, February 22, 2022 at 14:20:01
--

-- *****************************************************************************
-- Description: Cable modem extension MIB for Teleste transponders
-- 
-- Revision History:
-- -----------------
-- 
-- v4 22.2.2022 Sami Halen
-- - Bugfix: Renamed cmTunerPowerControl => cmTunerPowersaveControl and 
--   cmTunerPowerStatus => cmTunerPowersaveStatus and inverted their enable/disable values
-- 
-- v3 18.8.2021 Sami Halen
-- - Updated descriptions with transponder type differences
-- - Added AC6983 OIDs: cmConnCheckIPv6, cmIpProvMode, cmTunerPowerControl, 
--   cmTunerPowerStatus
-- - Removed: cmTelnetEnable, cmUsbEnable, cmEthernetEnable
-- 
-- v2 10.4.2017 Sami Halen
-- - Removed PLL and peripheral enables
-- 
-- v1 5.4.2017 Matti Susi
-- - First draft
-- 
-- ****************************************************************************
-- 

	TELESTE-CM-EXT-MIB DEFINITIONS ::= BEGIN
 
		IMPORTS
			OBJECT-TYPE			
				FROM RFC-1212			
			enterprises, IpAddress			
				FROM RFC1155-SMI;
	
	
--
-- Node definitions
--
	
-- This MIB module only describes the settings objects valid for
-- the cable modem part of Teleste AC698x DOCSIS transponder.
		-- 1.3.6.1.4.1.8595
		hitron OBJECT IDENTIFIER ::= { enterprises 8595 }

		
		-- 1.3.6.1.4.1.8595.1
		equipment OBJECT IDENTIFIER ::= { hitron 1 }

		
		-- 1.3.6.1.4.1.8595.1.400
		cableModem OBJECT IDENTIFIER ::= { equipment 400 }

		
		-- 1.3.6.1.4.1.8595.1.400.2
		cmExtensions OBJECT IDENTIFIER ::= { cableModem 2 }

		
		-- 1.3.6.1.4.1.8595.1.400.2.1
		cmControlExtensions OBJECT IDENTIFIER ::= { cmExtensions 1 }

		
-- Cable modem protocol and watchdog control settings.
		-- 1.3.6.1.4.1.8595.1.400.2.1.2
		cmMiscControl OBJECT IDENTIFIER ::= { cmControlExtensions 2 }

		
		-- 1.3.6.1.4.1.8595.1.400.2.1.2.32
		cmWebEnable OBJECT-TYPE
			SYNTAX INTEGER
				{
				bothDisable(0),
				lanOnly(1),
				rfOnly(2),
				bothEnable(3)
				}
			ACCESS read-write
			STATUS mandatory
			DESCRIPTION
				"HTTP protocol (WEB UI) enable/disable via RF and LAN interfaces.
				(LAN interface is not accessible in AC698x transponders.)
				This value is stored into non-volatile memory and be effective after next reboot."
			::= { cmMiscControl 32 }

		
		-- 1.3.6.1.4.1.8595.1.400.2.1.2.34
		cmConnCheckControl OBJECT-TYPE
			SYNTAX INTEGER
				{
				enabled(1),
				disabled(2)
				}
			ACCESS read-write
			STATUS mandatory
			DESCRIPTION
				"Connection Check Watchdog:
				This object is used to read the watchdog status (AC6980/1)
				or enable/disable the watchdog (AC6983)."
			::= { cmMiscControl 34 }

		
		-- 1.3.6.1.4.1.8595.1.400.2.1.2.35
		cmConnCheckIP OBJECT-TYPE
			SYNTAX IpAddress
			ACCESS read-write
			STATUS mandatory
			DESCRIPTION
				"Connection Check Watchdog:
				This object is used to setup the watchdog PING target IPv4 address."
			::= { cmMiscControl 35 }

		
		-- 1.3.6.1.4.1.8595.1.400.2.1.2.36
		cmConnCheckInterval OBJECT-TYPE
			SYNTAX INTEGER (0..86400)
			ACCESS read-write
			STATUS mandatory
			DESCRIPTION
				"Connection Check Watchdog:
				This object is used to setup the watchdog PING interval in seconds."
			::= { cmMiscControl 36 }

		
		-- 1.3.6.1.4.1.8595.1.400.2.1.2.37
		cmConnCheckCount OBJECT-TYPE
			SYNTAX INTEGER (0..1000)
			ACCESS read-write
			STATUS mandatory
			DESCRIPTION
				"Connection Check Watchdog:
				Number of failed PINGs before the watchdog resets the modem."
			::= { cmMiscControl 37 }

		
		-- 1.3.6.1.4.1.8595.1.400.2.1.2.39
		cmConnCheckRestart OBJECT-TYPE
			SYNTAX INTEGER
				{
				restart(1),
				default(2)
				}
			ACCESS read-write
			STATUS mandatory
			DESCRIPTION
				"Connection Check Watchdog:
				This object is used to take watchdog settings into use and (re)start the watchdog.
				Reading always returns value default(2)."
			::= { cmMiscControl 39 }

		
		-- 1.3.6.1.4.1.8595.1.400.2.1.2.40
		cmConnCheckIPv6 OBJECT-TYPE
			SYNTAX OCTET STRING (SIZE (0..63))
			ACCESS read-write
			STATUS mandatory
			DESCRIPTION
				"Connection Check Watchdog:
				This object is used to setup the watchdog PING target IPv6 address.
				AC6983 only."
			::= { cmMiscControl 40 }

		
		-- 1.3.6.1.4.1.8595.1.400.2.1.2.44
		cmIpProvMode OBJECT-TYPE
			SYNTAX INTEGER
				{
				ipv4(0),
				ipv6(1),
				mdd(4)
				}
			ACCESS read-write
			STATUS mandatory
			DESCRIPTION
				"This object is used to control the provisioning mode.
				Connection will be reset if different value is written.
				AC6983 only."
			::= { cmMiscControl 44 }

		
		-- 1.3.6.1.4.1.8595.1.400.2.1.2.45
		cmTunerPowersaveControl OBJECT-TYPE
			SYNTAX INTEGER
				{
				enable(1),
				disable(2)
				}
			ACCESS read-write
			STATUS mandatory
			DESCRIPTION
				"CM downstream tuner powersave control.
				When enabled (default), tuner is in powersave mode and transponder operates in 1x1 mode. 
				When disabled, tuner may be in full power mode and transponder operates in up to 8x4 mode.
				Tuner powertsave status can be read from cmTunerPowersaveStatus.
				Enabling FBC (Full Band Capture) automatically disables powersave mode.
				AC6983 only."
			::= { cmMiscControl 45 }

		
		-- 1.3.6.1.4.1.8595.1.400.2.1.2.46
		cmTunerPowersaveStatus OBJECT-TYPE
			SYNTAX INTEGER
				{
				enable(1),
				disable(2)
				}
			ACCESS read-only
			STATUS mandatory
			DESCRIPTION
				"CM downstream tuner powersave status.
				When cmTunerPowersaveControl is enabled, this value is always enabled.
				When cmTunerPowersaveControl is disabled, this value changes according to tuner powersave mode status.
				AC6983 only."
			::= { cmMiscControl 46 }

		
-- Cable modem interface control settings.
		-- 1.3.6.1.4.1.8595.1.400.7
		cmInterfaceControl OBJECT IDENTIFIER ::= { cableModem 7 }

		
		-- 1.3.6.1.4.1.8595.1.400.7.5
		cmTsempForwardingEnable OBJECT-TYPE
			SYNTAX INTEGER
				{
				enable(1),
				disable(2)
				}
			ACCESS read-write
			STATUS mandatory
			DESCRIPTION
				"This object is used to enable/disable Teleste proprietary TSEMP protocol
				forwarding towards the node/amplifier via the internal serial interface.
				Must be enabled to use remote TSEMP connection.
				This value is stored into non-volatile memory."
			::= { cmInterfaceControl 5 }

		
	
	END

--
-- TELESTE-CM-EXT-MIB.mib
--
