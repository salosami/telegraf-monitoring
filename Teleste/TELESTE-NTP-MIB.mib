--
-- TELESTE-NTP-MIB.mib
-- MIB generated by MG-SOFT Visual MIB Builder Version 4.0 Build 349
-- Tuesday, March 02, 2010 at 08:48:30
--

-- *****************************************************************************
-- Copyright (c) 2000-2010 by:
-- 
-- Teleste Corporation
-- Seponkatu 1
-- FIN-20660 Littoinen, Finland
-- tel. +358 2 2605 611
-- url: http://www.teleste.com
-- 
-- Description: Functional MIB module for NTP control
-- 
-- Revision History:
-- -----------------
-- 1.0 24.11.2009 Rainer Salminen
-- - first offcial release
-- 
-- ****************************************************************************
-- 

	TELESTE-NTP-MIB DEFINITIONS ::= BEGIN
 
		IMPORTS
			OBJECT-TYPE			
				FROM RFC-1212			
			IpAddress			
				FROM RFC1155-SMI			
			DisplayString			
				FROM RFC1213-MIB			
			ntpcontrol, DateAndTime			
				FROM TELESTE-ROOT-MIB;
	
	
	
--
-- Node definitions
--
	
-- Node definitions
		-- 1.3.6.1.4.1.3715.100.4.1
		ntpCurrentTime OBJECT-TYPE
			SYNTAX DateAndTime
			ACCESS read-write
			STATUS mandatory
			DESCRIPTION
				"Current device time since the Epoch (00:00:00 UTC, January 1, 1970),
				measured in seconds (POSIX)."
			::= { ntpcontrol 1 }

		
		-- 1.3.6.1.4.1.3715.100.4.2
		ntpTimeSyncInterval OBJECT-TYPE
			SYNTAX INTEGER
			ACCESS read-write
			STATUS mandatory
			DESCRIPTION
				"NTP time sync interval. Unit 1 second."
			::= { ntpcontrol 2 }

		
		-- 1.3.6.1.4.1.3715.100.4.3
		ntpManualSync OBJECT-TYPE
			SYNTAX INTEGER { ntpSyncNow(1) }
			ACCESS read-write
			STATUS mandatory
			DESCRIPTION
				"Setting this object to ntpSyncNow(1) initiates immediate
				NTP time synchronisation. Reading this object always returns the
				value ntpSyncNow(1)."
			::= { ntpcontrol 3 }

		
		-- 1.3.6.1.4.1.3715.100.4.4
		ntpTimeZone OBJECT-TYPE
			SYNTAX DisplayString
			ACCESS read-write
			STATUS mandatory
			DESCRIPTION
				"TimeZone in the same formats as used in TZ enviroment variable in POSIX systems.
				See for example: http://www.gnu.org/s/libc/manual/html_node/TZ-Variable.html
												
				Device need to support only one of the formats. The format returned from the device
				must be used to set the object's value. Other formats return BAD VALUE.
				
				Use of second format (std offset dst [offset],start[/time],end[/time]) with Mm.w.d
				specifier is recommended, but not mandatory.
								
				Example (format 2):
								
				Timezone definition
								
				EET-2EEST-3,M3.5.0/3,M10.5.0/4
								
				means East European time -2 hours from UTC, 
				East European summertime -3 hours from UTC,
				summertime begins on Sunday of the last week of March at 03:00, 
				and ends on Sunday of the last week of October at 04:00.
				
				See also http://www.twinsun.com/tz/tz-link.htm."
			::= { ntpcontrol 4 }

		
		-- 1.3.6.1.4.1.3715.100.4.5
		ntpServerTable OBJECT-TYPE
			SYNTAX SEQUENCE OF NtpServerEntry
			ACCESS not-accessible
			STATUS mandatory
			DESCRIPTION
				"A table of NTP server entries. Servers are contacted in
				the table index order."
			::= { ntpcontrol 5 }

		
		-- 1.3.6.1.4.1.3715.100.4.5.1
		ntpServerEntry OBJECT-TYPE
			SYNTAX NtpServerEntry
			ACCESS not-accessible
			STATUS mandatory
			INDEX { ntpServerIndex }
			::= { ntpServerTable 1 }

		
		NtpServerEntry ::=
			SEQUENCE { 
				ntpServerIndex
					INTEGER,
				ntpServerNetworkAddress
					IpAddress,
				ntpServerState
					INTEGER
			 }

		-- 1.3.6.1.4.1.3715.100.4.5.1.1
		ntpServerIndex OBJECT-TYPE
			SYNTAX INTEGER (1..5)
			ACCESS read-only
			STATUS mandatory
			DESCRIPTION
				"Index of the server entry"
			::= { ntpServerEntry 1 }

		
		-- 1.3.6.1.4.1.3715.100.4.5.1.2
		ntpServerNetworkAddress OBJECT-TYPE
			SYNTAX IpAddress
			ACCESS read-write
			STATUS mandatory
			DESCRIPTION
				"NTP server IP address."
			::= { ntpServerEntry 2 }

		
		-- 1.3.6.1.4.1.3715.100.4.5.1.3
		ntpServerState OBJECT-TYPE
			SYNTAX INTEGER
				{
				serverEnable(1),
				serverDisable(2)
				}
			ACCESS read-write
			STATUS mandatory
			DESCRIPTION
				"NTP server state:
				serverEnable(1)
				serverDisable(2)"
			::= { ntpServerEntry 3 }

		
	
	END

--
-- TELESTE-NTP-MIB.mib
--
