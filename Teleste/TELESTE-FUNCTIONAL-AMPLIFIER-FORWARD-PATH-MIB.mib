--
-- TELESTE-FUNCTIONAL-AMPLIFIER-FORWARD-PATH-MIB.mib
-- MIB generated by MG-SOFT Visual MIB Builder 2013 (64-bit) Version 9.0  Build 760
-- Wednesday, March 12, 2014 at 13:33:20
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-AMPLIFIER-FORWARD-PATH-MIB
-- 
-- Description:   MIB module describing Teleste functional amplifier forward path interface specific objects
-- 
-- Revision history:
-- -----------------
-- 1, 12.3.2014, Sami Kuusisto
-- - Initial version.
-- 
-- ****************************************************************************
-- 

	TELESTE-FUNCTIONAL-AMPLIFIER-FORWARD-PATH-MIB DEFINITIONS ::= BEGIN
 
		IMPORTS
			OBJECT-TYPE			
				FROM RFC-1212			
			functional			
				FROM TELESTE-ROOT-MIB;
	
	
	
--
-- Node definitions
--
	
		-- 1.3.6.1.4.1.3715.100.41
		amplifierForwardPath OBJECT IDENTIFIER ::= { functional 41 }

		
		-- 1.3.6.1.4.1.3715.100.41.1
		amplifierForwardPathXxx OBJECT-TYPE
			SYNTAX INTEGER
			ACCESS read-write
			STATUS mandatory
			DESCRIPTION
				"Forward path XXX description."
			::= { amplifierForwardPath 1 }

		
	
	END

--
-- TELESTE-FUNCTIONAL-AMPLIFIER-FORWARD-PATH-MIB.mib
--
