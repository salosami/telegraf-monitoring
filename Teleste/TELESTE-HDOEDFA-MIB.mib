--
-- TELESTE-HDOEDFA-MIB.mib
-- MIB generated by MG-SOFT Visual MIB Builder Version 4.0 Build 349
-- Tuesday, October 12, 2010 at 12:38:08
--

-- ****************************************************************************
-- Copyright (c) 2005-2010 by:
-- 
-- Teleste Corporation
-- Seponkatu 1
-- FIN-20660 Littoinen, Finland
-- tel. +358 2 2605 611
-- url: http://www.teleste.com
-- 
-- Module Name:   TELESTE-HDOEDFA-MIB
-- 
-- Description:   MIB module describing HDO EDFA objects
-- 
-- Revision History:
-- -----------------
-- 1.2 12.10.2010 Matti Susi
-- - moved all sysOIDs to TELESTE-HDO-MIB
-- 
-- 1.1 17.12.2009 Rainer Salminen and Sami Salo
-- -removed edfa2 group
-- 
-- 1.0 16.12.2009 Rainer Salminen and Sami Salo
-- -major changes
-- 
-- 0.21, 25.3.2009, Matti Susi
-- - editorial corrections to edfa2
-- 
-- 0.2, 17.3.2009, Matti Susi
-- - added edfa2
-- 
-- 0.1, 15.2.2006, Matti Susi
-- - initial version
-- 
-- ****************************************************************************
-- 

	TELESTE-HDOEDFA-MIB DEFINITIONS ::= BEGIN
 
		IMPORTS
			OBJECT-TYPE			
				FROM RFC-1212			
			TRAP-TYPE			
				FROM RFC-1215			
			sysUpTime, DisplayString			
				FROM RFC1213-MIB			
			oemodules			
				FROM TELESTE-HDO-MIB			
			teleste			
				FROM TELESTE-ROOT-MIB;
	
	
	
--
-- Node definitions
--
	
-- EDFA node definitions
		-- 1.3.6.1.4.1.3715.14.2.102
		edfa OBJECT IDENTIFIER ::= { oemodules 102 }

		
--  1.3.6.1.4.1.3715.14.2.102.1
		-- 1.3.6.1.4.1.3715.14.2.102.1
		edfaMeasurements OBJECT IDENTIFIER ::= { edfa 1 }

		
--  1.3.6.1.4.1.3715.14.2.102.1.1
		-- 1.3.6.1.4.1.3715.14.2.102.1.1
		inputPower OBJECT-TYPE
			SYNTAX INTEGER (-32768..32767)
			ACCESS read-only
			STATUS mandatory
			DESCRIPTION
				"Optical input power, unit dBm"
			::= { edfaMeasurements 1 }

		
--  1.3.6.1.4.1.3715.14.2.102.1.2
		-- 1.3.6.1.4.1.3715.14.2.102.1.2
		outputPower OBJECT-TYPE
			SYNTAX INTEGER (0..65536)
			ACCESS read-only
			STATUS mandatory
			DESCRIPTION
				"Optical output power, unit 0.1dBm"
			::= { edfaMeasurements 2 }

		
--  1.3.6.1.4.1.3715.14.2.102.1.3
		-- 1.3.6.1.4.1.3715.14.2.102.1.3
		pump1TECcurrent OBJECT-TYPE
			SYNTAX INTEGER (-32768..32767)
			ACCESS read-only
			STATUS mandatory
			DESCRIPTION
				"Pump 1 TEC current, unit mA"
			::= { edfaMeasurements 3 }

		
--  1.3.6.1.4.1.3715.14.2.102.1.4
		-- 1.3.6.1.4.1.3715.14.2.102.1.4
		pump2TECcurrent OBJECT-TYPE
			SYNTAX INTEGER (-32768..32767)
			ACCESS read-only
			STATUS mandatory
			DESCRIPTION
				"Pump 2 TEC current, unit mA"
			::= { edfaMeasurements 4 }

		
--  1.3.6.1.4.1.3715.14.2.102.1.5
		-- 1.3.6.1.4.1.3715.14.2.102.1.5
		pump3TECcurrent OBJECT-TYPE
			SYNTAX INTEGER (-32768..32767)
			ACCESS read-only
			STATUS mandatory
			DESCRIPTION
				"Pump 3 TEC current, unit mA"
			::= { edfaMeasurements 5 }

		
--  1.3.6.1.4.1.3715.14.2.102.1.6
		-- 1.3.6.1.4.1.3715.14.2.102.1.6
		pump1TEMP OBJECT-TYPE
			SYNTAX INTEGER (-128..127)
			ACCESS read-only
			STATUS mandatory
			DESCRIPTION
				"Pump 1 temperature, unit degC"
			::= { edfaMeasurements 6 }

		
--  1.3.6.1.4.1.3715.14.2.102.1.7
		-- 1.3.6.1.4.1.3715.14.2.102.1.7
		pump2TEMP OBJECT-TYPE
			SYNTAX INTEGER (-128..127)
			ACCESS read-only
			STATUS mandatory
			DESCRIPTION
				"Pump 2 temperature, unit degC"
			::= { edfaMeasurements 7 }

		
--  1.3.6.1.4.1.3715.14.2.102.1.8
		-- 1.3.6.1.4.1.3715.14.2.102.1.8
		pump3TEMP OBJECT-TYPE
			SYNTAX INTEGER (-128..127)
			ACCESS read-only
			STATUS mandatory
			DESCRIPTION
				"Pump 3 temperature, unit degC"
			::= { edfaMeasurements 8 }

		
--  1.3.6.1.4.1.3715.14.2.102.1.9
		-- 1.3.6.1.4.1.3715.14.2.102.1.9
		pump1BIAScurrent OBJECT-TYPE
			SYNTAX INTEGER (-32768..32767)
			ACCESS read-only
			STATUS mandatory
			DESCRIPTION
				"Pump 1 BIAS current, unit mA"
			::= { edfaMeasurements 9 }

		
--  1.3.6.1.4.1.3715.14.2.102.1.10
		-- 1.3.6.1.4.1.3715.14.2.102.1.10
		pump2BIAScurrent OBJECT-TYPE
			SYNTAX INTEGER (-32768..32767)
			ACCESS read-only
			STATUS mandatory
			DESCRIPTION
				"Pump 2 BIAS current, unit mA"
			::= { edfaMeasurements 10 }

		
--  1.3.6.1.4.1.3715.14.2.102.1.11
		-- 1.3.6.1.4.1.3715.14.2.102.1.11
		pump3BIAScurrent OBJECT-TYPE
			SYNTAX INTEGER (-32768..32767)
			ACCESS read-only
			STATUS mandatory
			DESCRIPTION
				"Pump 3 BIAS current, unit mA"
			::= { edfaMeasurements 11 }

		
--  1.3.6.1.4.1.3715.14.2.102.1.12
		-- 1.3.6.1.4.1.3715.14.2.102.1.12
		pump1CURRENTlimit OBJECT-TYPE
			SYNTAX INTEGER (-32768..32767)
			ACCESS read-only
			STATUS mandatory
			DESCRIPTION
				"Pump 1 current limit, unit mA "
			::= { edfaMeasurements 12 }

		
--  1.3.6.1.4.1.3715.14.2.102.1.13
		-- 1.3.6.1.4.1.3715.14.2.102.1.13
		pump2CURRENTlimit OBJECT-TYPE
			SYNTAX INTEGER (-32768..32767)
			ACCESS read-only
			STATUS mandatory
			DESCRIPTION
				"Pump 2 current limit, unit mA "
			::= { edfaMeasurements 13 }

		
--  1.3.6.1.4.1.3715.14.2.102.1.14
		-- 1.3.6.1.4.1.3715.14.2.102.1.14
		pump3CURRENTlimit OBJECT-TYPE
			SYNTAX INTEGER (-32768..32767)
			ACCESS read-only
			STATUS mandatory
			DESCRIPTION
				"Pump 3 current limit, unit mA "
			::= { edfaMeasurements 14 }

		
--  1.3.6.1.4.1.3715.14.2.102.1.15
		-- 1.3.6.1.4.1.3715.14.2.102.1.15
		workSTAT OBJECT-TYPE
			SYNTAX INTEGER (0..255)
			ACCESS read-only
			STATUS mandatory
			DESCRIPTION
				"EDFA LED indicator's status , workSTAT is a decimal number,it should be converted to binary number of eight
				bits. The meaning for each bit is as follows:
					 Bit 0: Power
				              Bit 1: Input power
				              Bit 2: Pump status
				              Bit 3: Output power
				              Bit 4: Over temp
				              Bit 5: Remote
				              Bit 6: reserved
				        Bit 7: reserved 
				The bit value of 0 means red light and bit value of 1 means green light.
				     "
			::= { edfaMeasurements 15 }

		
--  1.3.6.1.4.1.3715.14.2.102.1.16
		-- 1.3.6.1.4.1.3715.14.2.102.1.16
		pumpSTAT OBJECT-TYPE
			SYNTAX INTEGER
				{
				off(1),
				on(2)
				}
			ACCESS read-only
			STATUS mandatory
			DESCRIPTION
				"EDFA pump status"
			::= { edfaMeasurements 16 }

		
--  1.3.6.1.4.1.3715.14.2.102.2
		-- 1.3.6.1.4.1.3715.14.2.102.2
		edfaControl OBJECT IDENTIFIER ::= { edfa 2 }

		
--  1.3.6.1.4.1.3715.14.2.102.2.1
		-- 1.3.6.1.4.1.3715.14.2.102.2.1
		pump1BIAScurrentUP OBJECT-TYPE
			SYNTAX INTEGER (31)
			ACCESS read-write
			STATUS mandatory
			DESCRIPTION
				"Increase the bias current of pump 1. Please be careful to make pump current adjustment,since that will affect output power.
				write value (31)
				read  value (190)"
			::= { edfaControl 1 }

		
--  1.3.6.1.4.1.3715.14.2.102.2.2
		-- 1.3.6.1.4.1.3715.14.2.102.2.2
		pump1BIAScurrentDOWN OBJECT-TYPE
			SYNTAX INTEGER (39)
			ACCESS read-write
			STATUS mandatory
			DESCRIPTION
				"Decrease the bias current of pump 1. Please be careful to make pump current adjustment,since that will affect output power.
				write value (39)
				read  value (191)
				
				"
			::= { edfaControl 2 }

		
--  1.3.6.1.4.1.3715.14.2.102.2.3
		-- 1.3.6.1.4.1.3715.14.2.102.2.3
		pump2BIAScurrentUP OBJECT-TYPE
			SYNTAX INTEGER (34)
			ACCESS read-write
			STATUS mandatory
			DESCRIPTION
				"Increase the bias current of pump 2. Please be careful to make pump current adjustment,since that will affect output power. 
				write value (34)
				read  value (194)
				             "
			::= { edfaControl 3 }

		
--  1.3.6.1.4.1.3715.14.2.102.2.4
		-- 1.3.6.1.4.1.3715.14.2.102.2.4
		pump2BIAScurrentDOWN OBJECT-TYPE
			SYNTAX INTEGER (35)
			ACCESS read-write
			STATUS mandatory
			DESCRIPTION
				"Decrease the bias current of pump 2. Please be careful to make pump current adjustment,since that will affect output power.
				write value (35)
				read  value (195)
				"
			::= { edfaControl 4 }

		
--  1.3.6.1.4.1.3715.14.2.102.2.5
		-- 1.3.6.1.4.1.3715.14.2.102.2.5
		pump3BIAScurrentUP OBJECT-TYPE
			SYNTAX INTEGER (37)
			ACCESS read-write
			STATUS mandatory
			DESCRIPTION
				"Increase the bias current of pump 3. Please be careful to make pump current adjustment,since that will affect output power.
				write value (37)
				  read  value (197)
				"
			::= { edfaControl 5 }

		
--  1.3.6.1.4.1.3715.14.2.102.2.6
		-- 1.3.6.1.4.1.3715.14.2.102.2.6
		pump3BIAScurrentDOWN OBJECT-TYPE
			SYNTAX INTEGER (38)
			ACCESS read-write
			STATUS mandatory
			DESCRIPTION
				"Decrease the bias current of pump 3. Please be careful to make pump current adjustment,since that will affect output power.
				write value (38)
				read  value (198)
				"
			::= { edfaControl 6 }

		
--  1.3.6.1.4.1.3715.14.2.102.2.7
		-- 1.3.6.1.4.1.3715.14.2.102.2.7
		pumpControl OBJECT-TYPE
			SYNTAX INTEGER
				{
				turnoff(102),
				turnon(103)
				}
			ACCESS read-write
			STATUS mandatory
			DESCRIPTION
				"Remotely open and shut down pump laser. This operation can only 
				be carried out when the key on the front panel is on.
				"
			::= { edfaControl 7 }

		
--  1.3.6.1.4.1.3715.14.2.102.3
		-- 1.3.6.1.4.1.3715.14.2.102.3
		edfaStatus OBJECT IDENTIFIER ::= { edfa 3 }

		
--  1.3.6.1.4.1.3715.14.2.102.3.1
		-- 1.3.6.1.4.1.3715.14.2.102.3.1
		almMessageString OBJECT-TYPE
			SYNTAX DisplayString (SIZE (0..30))
			ACCESS read-only
			STATUS mandatory
			DESCRIPTION
				" Message giving detailed information on alarm traps."
			::= { edfaStatus 1 }

		
--  1.3.6.1.4.1.3715.14.2.102.3.2
		-- 1.3.6.1.4.1.3715.14.2.102.3.2
		almPump OBJECT-TYPE
			SYNTAX INTEGER
				{
				abnormal(1),
				normal(2)
				}
			ACCESS read-only
			STATUS mandatory
			DESCRIPTION
				"Pump's working state alarm. Changing from normal to abnormal state or vice versa will triger alarm."
			::= { edfaStatus 2 }

		
--  1.3.6.1.4.1.3715.14.2.102.3.3
		-- 1.3.6.1.4.1.3715.14.2.102.3.3
		almInput OBJECT-TYPE
			SYNTAX INTEGER
				{
				abnormal(1),
				normal(2)
				}
			ACCESS read-only
			STATUS mandatory
			DESCRIPTION
				"EDFA's input power alarm. Changing from normal to abnormal state 
				or vice versa will triger alarm."
			::= { edfaStatus 3 }

		
--  1.3.6.1.4.1.3715.14.2.102.3.4
		-- 1.3.6.1.4.1.3715.14.2.102.3.4
		almOutput OBJECT-TYPE
			SYNTAX INTEGER
				{
				abnormal(1),
				normal(2)
				}
			ACCESS read-only
			STATUS mandatory
			DESCRIPTION
				"EDFA's output power alarm.Changing from normal to abnormal state 
				or vice versa will triger alarm."
			::= { edfaStatus 4 }

		
--  1.3.6.1.4.1.3715.14.2.102.3.5
		-- 1.3.6.1.4.1.3715.14.2.102.3.5
		almPumptemp OBJECT-TYPE
			SYNTAX INTEGER
				{
				abnormal(1),
				normal(2)
				}
			ACCESS read-only
			STATUS mandatory
			DESCRIPTION
				"Pump's temperature alarm.Changing from normal to abnormal state 
				or vice versa will triger alarm. "
			::= { edfaStatus 5 }

		
--  1.3.6.1.4.1.3715.14.2.102.3.6
		-- 1.3.6.1.4.1.3715.14.2.102.3.6
		almDataCollection OBJECT-TYPE
			SYNTAX INTEGER (0..1)
			ACCESS read-write
			STATUS mandatory
			DESCRIPTION
				"Alarm for data Collection from EDFA.
				1 = data Collection broken (inactive for 30 seconds). 
				2 = data Collection normal.
				 "
			::= { edfaStatus 6 }

		
--  1.3.6.1.4.1.3715.14.2.102.4
		-- 1.3.6.1.4.1.3715.14.2.102.4
		edfatrap OBJECT IDENTIFIER ::= { edfa 4 }

		
--  1.3.6.1.4.1.3715.14.2.102.4.1
		-- 1.3.6.1.4.1.3715.14.2.102.4.1
		almTrap OBJECT-TYPE
			SYNTAX INTEGER (1..8)
			ACCESS read-only
			STATUS mandatory
			DESCRIPTION
				"Alarm trap. The meaning of its value is:
				1:Pump normal
				2:Pump abnormal
				3:Input normal
				4:Input abnormal
				5:Output normal
				6:Output abnormal
				7:Pump's temperature normal
				8:Pump's temperature abnormal
				"
			::= { edfatrap 1 }

		
	
--
-- Trap definitions
--
	
--  Trap definitions
-- 
		edfaAlarmEvent TRAP-TYPE 
			ENTERPRISE teleste
			VARIABLES { almMessageString, almTrap, sysUpTime }
			DESCRIPTION 
				"The SNMP trap that is generated when alarm occurs."
			::=  1

	
	END

--
-- TELESTE-HDOEDFA-MIB.mib
--
