--
-- TELESTE-DVX-MIB.mib
-- MIB generated by MG-SOFT Visual MIB Builder Version 4.0 Build 349
-- Thursday, December 21, 2006 at 14:48:12
--

-- *****************************************************************************
-- Copyright (c) 2000-2006 by:
-- 
-- Teleste Corporation
-- Seponkatu 1
-- FIN-20660 Littoinen, Finland
-- tel. +358 2 2605 611
-- url: http://www.teleste.com
-- 
-- Description: DVX module specific objects
-- 
-- Revision History:
-- -----------------
-- 1.0  21.12.2006 Matti Susi
-- - First official release
-- 
-- ****************************************************************************

	TELESTE-DVX-MIB DEFINITIONS ::= BEGIN
 
		IMPORTS
			OBJECT-TYPE			
				FROM RFC-1212			
			dvx			
				FROM TELESTE-ROOT-MIB;
	
	
--
-- Node definitions
--
	
		-- 1.3.6.1.4.1.3715.6.1
		dvm OBJECT IDENTIFIER ::= { dvx 1 }

		
		-- 1.3.6.1.4.1.3715.6.1.911
		dvm911 OBJECT IDENTIFIER ::= { dvm 911 }

		
		-- 1.3.6.1.4.1.3715.6.1.912
		dvm912 OBJECT IDENTIFIER ::= { dvm 912 }

		
		-- 1.3.6.1.4.1.3715.6.1.913
		dvm913 OBJECT IDENTIFIER ::= { dvm 913 }

		
		-- 1.3.6.1.4.1.3715.6.1.921
		dvm921 OBJECT IDENTIFIER ::= { dvm 921 }

		
		-- 1.3.6.1.4.1.3715.6.1.922
		dvm922 OBJECT IDENTIFIER ::= { dvm 922 }

		
		-- 1.3.6.1.4.1.3715.6.1.923
		dvm923 OBJECT IDENTIFIER ::= { dvm 923 }

		
		-- 1.3.6.1.4.1.3715.6.2
		dvp OBJECT IDENTIFIER ::= { dvx 2 }

		
		-- 1.3.6.1.4.1.3715.6.2.232
		dvp232 OBJECT IDENTIFIER ::= { dvp 232 }

		
		-- 1.3.6.1.4.1.3715.6.2.302
		dvp302 OBJECT IDENTIFIER ::= { dvp 302 }

		
		-- 1.3.6.1.4.1.3715.6.2.306
		dvp306 OBJECT IDENTIFIER ::= { dvp 306 }

		
		-- 1.3.6.1.4.1.3715.6.2.312
		dvp312 OBJECT IDENTIFIER ::= { dvp 312 }

		
		-- 1.3.6.1.4.1.3715.6.2.332
		dvp332 OBJECT IDENTIFIER ::= { dvp 332 }

		
		-- 1.3.6.1.4.1.3715.6.2.432
		dvp432 OBJECT IDENTIFIER ::= { dvp 432 }

		
		-- 1.3.6.1.4.1.3715.6.3
		dvq OBJECT IDENTIFIER ::= { dvx 3 }

		
		-- 1.3.6.1.4.1.3715.6.3.101
		dvq101 OBJECT IDENTIFIER ::= { dvq 101 }

		
		-- 1.3.6.1.4.1.3715.6.3.102
		dvq102 OBJECT IDENTIFIER ::= { dvq 102 }

		
		-- 1.3.6.1.4.1.3715.6.3.111
		dvq111 OBJECT IDENTIFIER ::= { dvq 111 }

		
		-- 1.3.6.1.4.1.3715.6.3.112
		dvq112 OBJECT IDENTIFIER ::= { dvq 112 }

		
		-- 1.3.6.1.4.1.3715.6.3.901
		dvq901 OBJECT IDENTIFIER ::= { dvq 901 }

		
		-- 1.3.6.1.4.1.3715.6.3.902
		dvq902 OBJECT IDENTIFIER ::= { dvq 902 }

		
		-- 1.3.6.1.4.1.3715.6.3.911
		dvq911 OBJECT IDENTIFIER ::= { dvq 911 }

		
		-- 1.3.6.1.4.1.3715.6.3.912
		dvq912 OBJECT IDENTIFIER ::= { dvq 912 }

		
		-- 1.3.6.1.4.1.3715.6.3.913
		dvq913 OBJECT IDENTIFIER ::= { dvq 913 }

		
		-- 1.3.6.1.4.1.3715.6.4
		dvt OBJECT IDENTIFIER ::= { dvx 4 }

		
		-- 1.3.6.1.4.1.3715.6.4.11
		dvt011 OBJECT IDENTIFIER ::= { dvt 11 }

		
		-- 1.3.6.1.4.1.3715.6.4.12
		dvt012 OBJECT IDENTIFIER ::= { dvt 12 }

		
		-- 1.3.6.1.4.1.3715.6.4.801
		dvt801 OBJECT IDENTIFIER ::= { dvt 801 }

		
		-- 1.3.6.1.4.1.3715.6.4.802
		dvt802 OBJECT IDENTIFIER ::= { dvt 802 }

		
		-- 1.3.6.1.4.1.3715.6.4.803
		dvt803 OBJECT IDENTIFIER ::= { dvt 803 }

		
		-- 1.3.6.1.4.1.3715.6.4.911
		dvt911 OBJECT IDENTIFIER ::= { dvt 911 }

		
		-- 1.3.6.1.4.1.3715.6.4.912
		dvt912 OBJECT IDENTIFIER ::= { dvt 912 }

		
		-- 1.3.6.1.4.1.3715.6.4.913
		dvt913 OBJECT IDENTIFIER ::= { dvt 913 }

		
		-- 1.3.6.1.4.1.3715.6.5
		dvd OBJECT IDENTIFIER ::= { dvx 5 }

		
		-- 1.3.6.1.4.1.3715.6.5.912
		dvd912 OBJECT IDENTIFIER ::= { dvd 912 }

		
		-- 1.3.6.1.4.1.3715.6.911
		dvx911 OBJECT IDENTIFIER ::= { dvx 911 }

		
		-- 1.3.6.1.4.1.3715.6.911.1
		ioInput1Status OBJECT-TYPE
			SYNTAX INTEGER
				{
				statusHigh(1),
				statusLow(2)
				}
			ACCESS read-only
			STATUS mandatory
			DESCRIPTION
				"I/O input 1 status"
			::= { dvx911 1 }

		
		-- 1.3.6.1.4.1.3715.6.911.2
		ioInput2Status OBJECT-TYPE
			SYNTAX INTEGER
				{
				statusHigh(1),
				statusLow(2)
				}
			ACCESS read-only
			STATUS mandatory
			DESCRIPTION
				"I/O input 2 status"
			::= { dvx911 2 }

		
		-- 1.3.6.1.4.1.3715.6.911.3
		ioInput3Status OBJECT-TYPE
			SYNTAX INTEGER
				{
				statusHigh(1),
				statusLow(2)
				}
			ACCESS read-only
			STATUS mandatory
			DESCRIPTION
				"I/O input 3 status"
			::= { dvx911 3 }

		
		-- 1.3.6.1.4.1.3715.6.911.4
		ioOutput1Status OBJECT-TYPE
			SYNTAX INTEGER
				{
				statusHigh(1),
				statusLow(2)
				}
			ACCESS read-only
			STATUS mandatory
			DESCRIPTION
				"I/O output 1 status"
			::= { dvx911 4 }

		
		-- 1.3.6.1.4.1.3715.6.911.5
		ioOutput2Status OBJECT-TYPE
			SYNTAX INTEGER
				{
				statusHigh(1),
				statusLow(2)
				}
			ACCESS read-only
			STATUS mandatory
			DESCRIPTION
				"I/O output 2 status"
			::= { dvx911 5 }

		
	
	END

--
-- TELESTE-DVX-MIB.mib
--
