--
-- TELESTE-FUNCTIONAL-NODE-FORWARD-PATH-MIB.mib
-- MIB generated by MG-SOFT Visual MIB Builder 2013 (64-bit) Version 9.0  Build 760
-- Wednesday, March 12, 2014 at 16:06:37
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-NODE-FORWARD-PATH-MIB
-- 
-- Description:   MIB module describing Teleste functional node forward path interface specific objects
-- 
-- Revision history:
-- -----------------
-- 1, 12.3.2014, Sami Kuusisto
-- - Initial version.
-- 
-- ****************************************************************************
-- 

	TELESTE-FUNCTIONAL-NODE-FORWARD-PATH-MIB DEFINITIONS ::= BEGIN
 
		IMPORTS
			OBJECT-TYPE			
				FROM RFC-1212			
			functional			
				FROM TELESTE-ROOT-MIB;
	
	
	
--
-- Node definitions
--
	
		-- 1.3.6.1.4.1.3715.100.43
		nodeForwardPath OBJECT IDENTIFIER ::= { functional 43 }

		
		-- 1.3.6.1.4.1.3715.100.43.1
		nodeForwardPathOpticalInputStatus OBJECT-TYPE
			SYNTAX INTEGER
				{
				input1(1),
				input2(2),
				input1and2(3)
				}
			ACCESS read-only
			STATUS mandatory
			DESCRIPTION
				"Active optical input status:
				1 = input 1
				2 = input 2
				3 = input 1 and input 2"
			::= { nodeForwardPath 1 }

		
		-- 1.3.6.1.4.1.3715.100.43.2
		nodeForwardPathOpticalInputControl OBJECT-TYPE
			SYNTAX INTEGER
				{
				input1(1),
				input2(2),
				input1and2(3)
				}
			ACCESS read-write
			STATUS mandatory
			DESCRIPTION
				"Active optical input control:
				1 = input 1
				2 = input 2
				3 = input 1 and input 2"
			::= { nodeForwardPath 2 }

		
	
	END

--
-- TELESTE-FUNCTIONAL-NODE-FORWARD-PATH-MIB.mib
--
