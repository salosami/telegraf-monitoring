--
-- TELESTE-TRAP-MIB.mib
-- MIB generated by MG-SOFT Visual MIB Builder Version 4.0 Build 349
-- Tuesday, October 12, 2010 at 12:40:37
--

-- *****************************************************************************
-- Copyright (c) 2009-2010 by:
-- 
-- Teleste Corporation
-- Seponkatu 1
-- FIN-20660 Littoinen, Finland
-- tel. +358 2 2605 611
-- url: http://www.teleste.com
-- 
-- Description: Trap parameters and a table of trap receivers
-- 
-- Revision History:
-- -----------------
-- 1.1 12.10.2010 Matti Susi
-- - First official release
-- 
-- ****************************************************************************
-- 

	TELESTE-TRAP-MIB DEFINITIONS ::= BEGIN
 
		IMPORTS
			OBJECT-TYPE			
				FROM RFC-1212			
			IpAddress			
				FROM RFC1155-SMI			
			DisplayString			
				FROM RFC1213-MIB			
			functional			
				FROM TELESTE-ROOT-MIB;
	
	
	
--
-- Node definitions
--
	
-- This section contains element's common control parameters.
-- 
		-- 1.3.6.1.4.1.3715.100.101
		trapControl OBJECT IDENTIFIER ::= { functional 101 }

		
		-- 1.3.6.1.4.1.3715.100.101.1
		trapSending OBJECT-TYPE
			SYNTAX INTEGER
				{
				enabled(1),
				disabled(2)
				}
			ACCESS read-write
			STATUS mandatory
			DESCRIPTION
				"Trap sending master switch.
				Enables/disables trap sending:
				enabled(1) = traps are sent to enabled IP addresses in trapReceiverTable
				disabled(2) = all trap sending is disabled"
			::= { trapControl 1 }

		
		-- 1.3.6.1.4.1.3715.100.101.2
		trapDelay OBJECT-TYPE
			SYNTAX INTEGER
			ACCESS read-write
			STATUS mandatory
			DESCRIPTION
				"The first trap placed into empty trap queue should be sent 
				after the initial delay specified in this object.
				
				- Unit 1 ms
				- Minimum value 0 (0 ms)
				- Maximum value 60000 (60 seconds)
				- Default value 1000 (1 seconds)
				
				The purpose of this parameter is to avoid trap storms."
			::= { trapControl 2 }

		
		-- 1.3.6.1.4.1.3715.100.101.3
		trapInterval OBJECT-TYPE
			SYNTAX INTEGER
			ACCESS read-write
			STATUS mandatory
			DESCRIPTION
				"The minimum interval between two succesive traps.
				- Unit 1 milliseconds
				- Minimum value 0 (send as fast as possible)
				- Maximum value 10000 (10 seconds)
				- Default value is 1000 (1 second)"
			::= { trapControl 3 }

		
		-- 1.3.6.1.4.1.3715.100.101.4
		trapLifeTime OBJECT-TYPE
			SYNTAX INTEGER
			ACCESS read-write
			STATUS mandatory
			DESCRIPTION
				"The maximum time a trap stays in the trap queue waiting
				for sending.
				- Unit 1 second.
				- Minimum value 10
				- Maximum value 300
				- Default value 60"
			::= { trapControl 4 }

		
		-- 1.3.6.1.4.1.3715.100.101.5
		numberOfTrapReceivers OBJECT-TYPE
			SYNTAX INTEGER
			ACCESS read-only
			STATUS mandatory
			DESCRIPTION
				"Number of entries in the trapReceiverTable. 
				At least one trap receiver entry must be supported."
			::= { trapControl 5 }

		
		-- 1.3.6.1.4.1.3715.100.101.6
		trapReceiverTable OBJECT-TYPE
			SYNTAX SEQUENCE OF TrapReceiverEntry
			ACCESS not-accessible
			STATUS mandatory
			DESCRIPTION
				"A table of trap receiver addresses, ports and
				communities. The number of entries is given by 
				numberOfTrapReceivers. An entry is deleted from this
				table by setting its IP address to '0.0.0.0'.
				"
			::= { trapControl 6 }

		
		-- 1.3.6.1.4.1.3715.100.101.6.1
		trapReceiverEntry OBJECT-TYPE
			SYNTAX TrapReceiverEntry
			ACCESS not-accessible
			STATUS mandatory
			INDEX { receiverEntryId }
			::= { trapReceiverTable 1 }

		
		TrapReceiverEntry ::=
			SEQUENCE { 
				receiverEntryId
					INTEGER,
				receiverAddress
					IpAddress,
				receiverPort
					INTEGER,
				receiverCommunity
					DisplayString,
				receiverEnable
					INTEGER
			 }

		-- 1.3.6.1.4.1.3715.100.101.6.1.1
		receiverEntryId OBJECT-TYPE
			SYNTAX INTEGER (1..255)
			ACCESS read-only
			STATUS mandatory
			DESCRIPTION
				"Unique table index. Makes possible to have several 
				ip-address of 0.0.0.0 entries so that no mechanism
				for row manipulation of table is needed."
			::= { trapReceiverEntry 1 }

		
		-- 1.3.6.1.4.1.3715.100.101.6.1.2
		receiverAddress OBJECT-TYPE
			SYNTAX IpAddress
			ACCESS read-write
			STATUS mandatory
			DESCRIPTION
				"IP address of the SNMP manager receiving traps."
			::= { trapReceiverEntry 2 }

		
		-- 1.3.6.1.4.1.3715.100.101.6.1.3
		receiverPort OBJECT-TYPE
			SYNTAX INTEGER (1..65535)
			ACCESS read-write
			STATUS mandatory
			DESCRIPTION
				"Trap UDP port number. 
				Default port is the standard trap port 162."
			::= { trapReceiverEntry 3 }

		
		-- 1.3.6.1.4.1.3715.100.101.6.1.4
		receiverCommunity OBJECT-TYPE
			SYNTAX DisplayString
			ACCESS read-write
			STATUS mandatory
			DESCRIPTION
				"Community string for the trap receiver.
				
				The agent is allowed to limit the length of the string. 
				Minimum length of eight characters must be supported.
				"
			::= { trapReceiverEntry 4 }

		
		-- 1.3.6.1.4.1.3715.100.101.6.1.5
		receiverEnable OBJECT-TYPE
			SYNTAX INTEGER
				{
				enabled(1),
				disabled(2)
				}
			ACCESS read-write
			STATUS mandatory
			DESCRIPTION
				"State of the trap receiver entry:
				
				enabled(1) = traps are sent to the given entry
				disabled(2) = traps are not sent to the given entry"
			::= { trapReceiverEntry 5 }

		
	
	END

--
-- TELESTE-TRAP-MIB.mib
--
