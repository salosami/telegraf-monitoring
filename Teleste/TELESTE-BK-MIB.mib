--
-- TELESTE-BK-MIB.mib
-- MIB generated by MG-SOFT Visual MIB Builder 2021 (64-bit) Version 15.00  Build 1510
-- Tuesday, September 17, 2024 at 10:27:44
--

-- ****************************************************************************
-- Copyright (c) 2000-2024
-- Teleste Corporation
-- Telestenkatu 1
-- FI-20660 Littoinen, Finland
-- tel. +358 2 2605 611
-- url: http://www.teleste.com
-- 
-- Description: BK product specific MIB module
-- 
-- Revision History:
-- -----------------
-- 1.30, 17.9.2024 Sami Halen
-- - Added BKE148, BKE288 and BKE428 to known EQUs for rwSVrEqualiserType and aVrMainEqualiserType.
-- - Changed aVrHighPilotFrequency and aVrLowPilotFrequency from read-only to read-write.
-- 
-- 1.29, 9.4.2024 Sami Halen
-- - Added BKR700, BKT690 and BKC670 related OIDs:
--   - cVrForwardFrequencyMode
--   - cVrReturnFrequencyMode
--   - rwSVrA4PortMode
--   - rwSVrFrequencyMode
--   - aVrHighPilotFrequency
--   - aVrLowPilotFrequency
-- - Added BKE003, BKE14, BKE28 and BKE42 to known EQUs for rwSVrEqualiserType and aVrMainEqualiserType.
-- 
-- 1.28, 23.12.2021 Sami Kuusisto
-- - Added BKD200.
-- 
-- 1.27, 12.1.2015 Sami Halen
-- - Added BKO902 related OIDs oTrTx2Gain and oTrRxGain to oTrEntry
-- 
-- 1.26, 21.1.2014 Sami Halen
-- - Added BKO902 related OIDs to oTrEntry (1.3.6.1.4.1.3715.3.3.6.1.35...58)
-- 
-- 1.25, 20.8.2013 Sami Kuusisto
-- - Add BKE902 text in parallel to BKE901 to some of sEqTable entries.
-- - sEqPeak1Gain max to 1.40 dB
-- - sEqPeak3Gain max to 1.5 dB, peak@170 MHz
-- 
-- 1.24, 5.6.2013 Sami Halen
-- - added strVGtTable
-- 
-- 1.23, 3.9.2012 Sami Halen, Matti Susi
-- - added sEqNetworkType and sEqNotch2FreqRange
-- 
-- 1.22, 19.11.2009 Matti Susi
-- - cVr slope value range changed to enumerated for BKC629
-- - Fine tuned oTrRxOutputMode description
-- 
-- 1.21, 26.3.2008 Matti Susi
-- - added object rwSVrNotchControl
-- - extended rwSVrEqualiserType enumeration
-- - changed sEqGain value range to fit BKE901
-- 
-- 1.20, 16.1.2008 Matti Susi
-- - new objects and name changes for BKE901 support
-- 
-- 1.19, 21.9.2006 Matti Susi
-- - changed necModemTxLevel value ranges due to BKC903
-- - some object names fine tuned and harmonised
-- 
-- 1.18, 19.6.2006 Matti Susi
-- - added object oTrTxWavelength
-- 
-- 1.17, 22.3.2005 Matti Susi
-- - added system equaliser section
-- - added aVrLowEndPeak object
-- 
-- 1.16, 2.12.2004 Matti Susi
-- - aVrGain low limit changed
-- 
-- 1.15, 23.8.2004 Matti Susi
-- - added oRxTable
-- - added object oTrRxOutputLevelOffset
-- - editorial changes (comments refined)
-- 
-- 1.14, 18.3.2004 Matti Susi
-- - necModemRegState enumerations completed
-- 
-- 1.13, 1.9.2003 Matti Susi
-- - oTrLinkStatus enumerations fine tuned
-- 
-- 1.12, 20.3.2003 Matti Susi
-- - small ACCESS corrections in aVrTable
-- 
-- 1.11, 7.3.2003 Matti Susi
-- - table and object names harmonised with BK-OptiFlex family
-- - some object changed to optional
-- 
-- 1.11, 10.2.2003 Matti Susi
-- - cAmpEntry childs numbered
-- - oTrxEntry childs numbered
-- 
-- 1.1, 13.1.2003 Matti Susi
-- - preAmp low pilot objects inserted
-- - oTrxTxPowerHiHi and oTrxTxPowerHi objects added
-- - some oTrx objects changed to optional
-- 
-- 1.0, 12.12.2002 Matti Susi
-- - initial official release
-- - rAmp A port enumeration -40dB -> -50dB
-- - mctrlTxLevelStatus object removed
-- 
-- ****************************************************************************

	TELESTE-BK-MIB DEFINITIONS ::= BEGIN
 
		IMPORTS
			OBJECT-TYPE			
				FROM RFC-1212			
			moduleId			
				FROM TELESTE-COMMON-MIB			
			bk, Uint16, Int16			
				FROM TELESTE-ROOT-MIB;
	
	
	
--
-- Node definitions
--
	
-- BK station specific objects:
		-- 1.3.6.1.4.1.3715.3.1
		bkStation OBJECT IDENTIFIER ::= { bk 1 }

		
		-- 1.3.6.1.4.1.3715.3.1.1
		bkStationDc24v OBJECT-TYPE
			SYNTAX Uint16 (0..3000)
			ACCESS read-only
			STATUS mandatory
			DESCRIPTION
				"24 VDC measured voltage. Unit 0.01 volt."
			::= { bkStation 1 }

		
		-- 1.3.6.1.4.1.3715.3.1.2
		bkStationDc24vHiHi OBJECT-TYPE
			SYNTAX Uint16 (2000..3000)
			ACCESS read-write
			STATUS mandatory
			DESCRIPTION
				"24 VDC high alarm limit. Unit 0.01 volt."
			::= { bkStation 2 }

		
		-- 1.3.6.1.4.1.3715.3.1.3
		bkStationDc24vLoLo OBJECT-TYPE
			SYNTAX Uint16 (2000..3000)
			ACCESS read-write
			STATUS mandatory
			DESCRIPTION
				"24 VDC low alarm limit. Unit 0.01 volt."
			::= { bkStation 3 }

		
		-- 1.3.6.1.4.1.3715.3.1.4
		bkStationDc24vDeadband OBJECT-TYPE
			SYNTAX Uint16 (10..200)
			ACCESS read-write
			STATUS mandatory
			DESCRIPTION
				"24 VDC deadband. Unit 0.01 volt."
			::= { bkStation 4 }

		
		-- 1.3.6.1.4.1.3715.3.1.5
		bkStationDc6v5 OBJECT-TYPE
			SYNTAX Uint16 (0..1000)
			ACCESS read-only
			STATUS mandatory
			DESCRIPTION
				"6.5 VDC voltage. Unit 0.01 volt."
			::= { bkStation 5 }

		
		-- 1.3.6.1.4.1.3715.3.1.6
		bkStationDc6v5HiHi OBJECT-TYPE
			SYNTAX Uint16 (500..800)
			ACCESS read-write
			STATUS mandatory
			DESCRIPTION
				"6.5 VDC high alarm limit. Unit 0.01 volt."
			::= { bkStation 6 }

		
		-- 1.3.6.1.4.1.3715.3.1.7
		bkStationDc6v5LoLo OBJECT-TYPE
			SYNTAX Uint16 (500..800)
			ACCESS read-write
			STATUS mandatory
			DESCRIPTION
				"6.5 VDC low alarm limit. Unit 0.01 volt."
			::= { bkStation 7 }

		
		-- 1.3.6.1.4.1.3715.3.1.8
		bkStationDc6v5Deadband OBJECT-TYPE
			SYNTAX Uint16 (10..200)
			ACCESS read-write
			STATUS mandatory
			DESCRIPTION
				"6.5 VDC deadband. Unit 0.01 volt."
			::= { bkStation 8 }

		
		-- 1.3.6.1.4.1.3715.3.1.9
		bkStationDc6v5Current OBJECT-TYPE
			SYNTAX Uint16 (0..150)
			ACCESS read-only
			STATUS mandatory
			DESCRIPTION
				"6.5 VDC current. Unit 0.01 amp."
			::= { bkStation 9 }

		
		-- 1.3.6.1.4.1.3715.3.1.10
		bkStationDc6v5CurrentHiHi OBJECT-TYPE
			SYNTAX Uint16 (0..200)
			ACCESS read-write
			STATUS mandatory
			DESCRIPTION
				"6.5 VDC current high alarm limit. Unit 0.01 amp."
			::= { bkStation 10 }

		
		-- 1.3.6.1.4.1.3715.3.1.11
		bkStationDc6v5CurrentLo OBJECT-TYPE
			SYNTAX Uint16 (0..200)
			ACCESS read-write
			STATUS mandatory
			DESCRIPTION
				"6.5 VDC current low warning limit. Unit 0.01 amp."
			::= { bkStation 11 }

		
		-- 1.3.6.1.4.1.3715.3.1.12
		bkStationDc6v5CurrentDeadband OBJECT-TYPE
			SYNTAX Uint16 (10..100)
			ACCESS read-write
			STATUS mandatory
			DESCRIPTION
				"6.5 VDC current deadband. Unit 0.01 amp."
			::= { bkStation 12 }

		
		-- 1.3.6.1.4.1.3715.3.1.13
		bkStationAc1Voltage OBJECT-TYPE
			SYNTAX Uint16 (0..10000)
			ACCESS read-only
			STATUS mandatory
			DESCRIPTION
				"AC1 voltage. Unit 0.01 volt."
			::= { bkStation 13 }

		
		-- 1.3.6.1.4.1.3715.3.1.14
		bkStationAc1VoltageHiHi OBJECT-TYPE
			SYNTAX Uint16 (0..10000)
			ACCESS read-write
			STATUS mandatory
			DESCRIPTION
				"AC1 voltage high alarm limit. Unit 0.01 volt."
			::= { bkStation 14 }

		
		-- 1.3.6.1.4.1.3715.3.1.15
		bkStationAc1VoltageLoLo OBJECT-TYPE
			SYNTAX Uint16 (0..10000)
			ACCESS read-write
			STATUS mandatory
			DESCRIPTION
				"AC1 voltage low alarm limit. Unit 0.01 volt."
			::= { bkStation 15 }

		
		-- 1.3.6.1.4.1.3715.3.1.16
		bkStationAc1Deadband OBJECT-TYPE
			SYNTAX Uint16 (50..5000)
			ACCESS read-write
			STATUS mandatory
			DESCRIPTION
				"AC1 voltage deadband. Unit 0.01 volt."
			::= { bkStation 16 }

		
		-- 1.3.6.1.4.1.3715.3.1.17
		bkStationAc1Current OBJECT-TYPE
			SYNTAX Uint16 (0..2000)
			ACCESS read-only
			STATUS mandatory
			DESCRIPTION
				"AC1 current. Unit 0.01 amp."
			::= { bkStation 17 }

		
		-- 1.3.6.1.4.1.3715.3.1.18
		bkStationAc1CurrentHiHi OBJECT-TYPE
			SYNTAX Uint16 (0..2000)
			ACCESS read-write
			STATUS mandatory
			DESCRIPTION
				"AC1 current high alarm limit. Unit 0.01 amp."
			::= { bkStation 18 }

		
		-- 1.3.6.1.4.1.3715.3.1.19
		bkStationAc1CurrentLo OBJECT-TYPE
			SYNTAX Uint16 (0..2000)
			ACCESS read-write
			STATUS mandatory
			DESCRIPTION
				"AC1 current low warning limit. Unit 0.01 amp."
			::= { bkStation 19 }

		
		-- 1.3.6.1.4.1.3715.3.1.20
		bkStationAc1CurrentDeadband OBJECT-TYPE
			SYNTAX Uint16 (10..200)
			ACCESS read-write
			STATUS mandatory
			DESCRIPTION
				"AC1 current deadband. Unit 0.01 amp."
			::= { bkStation 20 }

		
		-- 1.3.6.1.4.1.3715.3.1.21
		bkStationAc2Current OBJECT-TYPE
			SYNTAX Uint16 (0..2000)
			ACCESS read-only
			STATUS mandatory
			DESCRIPTION
				"AC2 current. Unit 0.01 amp."
			::= { bkStation 21 }

		
		-- 1.3.6.1.4.1.3715.3.1.22
		bkStationAc2CurrentHiHi OBJECT-TYPE
			SYNTAX Uint16 (0..2000)
			ACCESS read-write
			STATUS mandatory
			DESCRIPTION
				"AC2 current high alarm limit. Unit 0.01 amp."
			::= { bkStation 22 }

		
		-- 1.3.6.1.4.1.3715.3.1.23
		bkStationAc2CurrentLo OBJECT-TYPE
			SYNTAX Uint16 (0..2000)
			ACCESS read-write
			STATUS mandatory
			DESCRIPTION
				"AC2 current low warning limit. Unit 0.01 amp."
			::= { bkStation 23 }

		
		-- 1.3.6.1.4.1.3715.3.1.24
		bkStationAc2CurrentDeadband OBJECT-TYPE
			SYNTAX Uint16 (10..200)
			ACCESS read-write
			STATUS mandatory
			DESCRIPTION
				"AC2 current deadband. Unit 0.01 amp."
			::= { bkStation 24 }

		
		-- 1.3.6.1.4.1.3715.3.1.25
		bkStationPsuAlarm OBJECT-TYPE
			SYNTAX INTEGER
				{
				noAlarm(1),
				alarm(2)
				}
			ACCESS read-only
			STATUS mandatory
			DESCRIPTION
				"Status of the PSU module alarm line:
				1 = both PSU's OK
				2 = one PSU reports a fault"
			::= { bkStation 25 }

		
-- BK module specific objects
		-- 1.3.6.1.4.1.3715.3.3
		bkModules1 OBJECT IDENTIFIER ::= { bk 3 }

		
-- necTable contains element specific information for
-- Network Element Controller (BKC90X) modules in a BK
-- system.
-- 
-- Note that index is moduleIndex which is column in 
-- the moduleTable defined in TELESTE-COMMON-MIB. Rows in
-- this table exist only if there are corresponding
-- rows in the moduleTable.
-- 
		-- 1.3.6.1.4.1.3715.3.3.1
		necTable OBJECT-TYPE
			SYNTAX SEQUENCE OF NecEntry
			ACCESS not-accessible
			STATUS mandatory
			DESCRIPTION
				"necTable contains element specific information for
				Network Element Controller (BKC90X) modules in a BK
				system."
			::= { bkModules1 1 }

		
		-- 1.3.6.1.4.1.3715.3.3.1.1
		necEntry OBJECT-TYPE
			SYNTAX NecEntry
			ACCESS not-accessible
			STATUS mandatory
			INDEX { moduleId }
			::= { necTable 1 }

		
		NecEntry ::=
			SEQUENCE { 
				necModemRxLevel
					Uint16,
				necModemRxLevelHi
					Uint16,
				necModemRxLevelLo
					Uint16,
				necModemRxLevelDeadband
					Uint16,
				necModemRxFrequency
					Uint16,
				necModemRxScanMin
					Uint16,
				necModemRxScanMax
					Uint16,
				necModemTxFrequency
					Uint16,
				necModemTxLevelMin
					Uint16,
				necModemTxLevelMax
					Uint16,
				necModemRegState
					INTEGER,
				necModemReceived
					Uint16,
				necModemBad
					Uint16,
				necModemSent
					Uint16,
				necModemResetStat
					INTEGER,
				necModemChnlDescTimeout
					Uint16,
				necModemPollTimeout
					Uint16,
				necHwError
					INTEGER,
				necRxLevelStatus
					INTEGER,
				necTemperatureStatus
					INTEGER
			 }

		-- 1.3.6.1.4.1.3715.3.3.1.1.1
		necModemRxLevel OBJECT-TYPE
			SYNTAX Uint16 (0..10000)
			ACCESS read-only
			STATUS mandatory
			DESCRIPTION
				"Received data carrier level. Unit 0.01 dBµV."
			::= { necEntry 1 }

		
		-- 1.3.6.1.4.1.3715.3.3.1.1.2
		necModemRxLevelHi OBJECT-TYPE
			SYNTAX Uint16 (0..10000)
			ACCESS read-write
			STATUS mandatory
			DESCRIPTION
				"Data carrier level high warning limit. Unit 0.01 dBµV."
			::= { necEntry 2 }

		
		-- 1.3.6.1.4.1.3715.3.3.1.1.3
		necModemRxLevelLo OBJECT-TYPE
			SYNTAX Uint16 (0..10000)
			ACCESS read-write
			STATUS mandatory
			DESCRIPTION
				"Data carrier level low warning limit. Unit 0.01 dBµV."
			::= { necEntry 3 }

		
		-- 1.3.6.1.4.1.3715.3.3.1.1.4
		necModemRxLevelDeadband OBJECT-TYPE
			SYNTAX Uint16 (100..1000)
			ACCESS read-write
			STATUS mandatory
			DESCRIPTION
				"Data carrier level deadband. Unit 0.01 dBµV."
			::= { necEntry 4 }

		
		-- 1.3.6.1.4.1.3715.3.3.1.1.5
		necModemRxFrequency OBJECT-TYPE
			SYNTAX Uint16 (8500..11800)
			ACCESS read-only
			STATUS mandatory
			DESCRIPTION
				"Modem current receive frequency. Unit 10 kHz."
			::= { necEntry 5 }

		
		-- 1.3.6.1.4.1.3715.3.3.1.1.6
		necModemRxScanMin OBJECT-TYPE
			SYNTAX Uint16 (8500..11800)
			ACCESS read-write
			STATUS mandatory
			DESCRIPTION
				"Modem receive scanning minimum frequency. Unit 10 kHz."
			::= { necEntry 6 }

		
		-- 1.3.6.1.4.1.3715.3.3.1.1.7
		necModemRxScanMax OBJECT-TYPE
			SYNTAX Uint16 (8500..11800)
			ACCESS read-write
			STATUS mandatory
			DESCRIPTION
				"Modem receive scanning maximum frequency. Unit 10 kHz."
			::= { necEntry 7 }

		
		-- 1.3.6.1.4.1.3715.3.3.1.1.8
		necModemTxFrequency OBJECT-TYPE
			SYNTAX Uint16 (500..1500)
			ACCESS read-only
			STATUS mandatory
			DESCRIPTION
				"Modem transmit frequency. Unit 10 kHz."
			::= { necEntry 8 }

		
		-- 1.3.6.1.4.1.3715.3.3.1.1.9
		necModemTxLevelMin OBJECT-TYPE
			SYNTAX Uint16 (7300..9000)
			ACCESS read-write
			STATUS mandatory
			DESCRIPTION
				"Modem minimum transmit level. Unit 0.01 dBµV.
				
				The module limits the values to the specified range as follows:
				
				BKC902: The accepted range is 8000-9000 (80-90 dBuV). If a Set message
				contains a value outside this range, a 'Bad value' is returned and the
				current value is maintained.
				
				BKC903: The accepted range is 7300-8300 (73-83 dBuV). If a Set message
				contains a value outside this range, the module sets the value to the 
				corresponding limit.
				
				For a fixed level setting, the minimum and maximum transmit level values
				should equal."
			::= { necEntry 9 }

		
		-- 1.3.6.1.4.1.3715.3.3.1.1.10
		necModemTxLevelMax OBJECT-TYPE
			SYNTAX Uint16 (7300..9000)
			ACCESS read-write
			STATUS mandatory
			DESCRIPTION
				"Modem maximum transmit level. Unit 0.01 dBµV.
				
				The module limits the values to the specified range as follows:
				
				BKC902: The accepted range is 8000-9000 (80-90 dBuV). If a Set message
				contains a value outside this range, a 'Bad value' is returned and the
				current value is maintained.
				
				BKC903: The accepted range is 7300-8300 (73-83 dBuV). If a Set message
				contains a value outside this range, the module sets the value to the 
				corresponding limit.
				
				For a fixed level setting, the minimum and maximum transmit level values
				should equal."
			::= { necEntry 10 }

		
		-- 1.3.6.1.4.1.3715.3.3.1.1.11
		necModemRegState OBJECT-TYPE
			SYNTAX INTEGER
				{
				regSettingRx(1),
				regNoCarrier(2),
				regWaitChannelInfo(3),
				regSettingTxFreq(4),
				regTxStabilisation(5),
				regSettingTxLevel(6),
				regPreparing(7),
				regStarting(8),
				regInProgress(9),
				regWaitConfirm(10),
				regComplete(11)
				}
			ACCESS read-only
			STATUS mandatory
			DESCRIPTION
				"Modem registration state:
				1 = setting RX frequency
				2 = no data carrier
				3 = waiting for channel infor (CHNLDESC)
				4 = setting TX frequency
				5 = waiting for TX stabilisation
				6 = setting TX level
				7 = preparing registration
				8 = registration starting
				9 = registration in progress
				10 = waiting for confimation
				11 = registration complete"
			::= { necEntry 11 }

		
		-- 1.3.6.1.4.1.3715.3.3.1.1.12
		necModemReceived OBJECT-TYPE
			SYNTAX Uint16
			ACCESS read-only
			STATUS mandatory
			DESCRIPTION
				"Number of received non-MAC datagrams."
			::= { necEntry 12 }

		
		-- 1.3.6.1.4.1.3715.3.3.1.1.13
		necModemBad OBJECT-TYPE
			SYNTAX Uint16
			ACCESS read-only
			STATUS mandatory
			DESCRIPTION
				"Number of received invalid non-MAC datagrams."
			::= { necEntry 13 }

		
		-- 1.3.6.1.4.1.3715.3.3.1.1.14
		necModemSent OBJECT-TYPE
			SYNTAX Uint16
			ACCESS read-only
			STATUS mandatory
			DESCRIPTION
				"Number of sent non-MAC datagrams."
			::= { necEntry 14 }

		
		-- 1.3.6.1.4.1.3715.3.3.1.1.15
		necModemResetStat OBJECT-TYPE
			SYNTAX INTEGER
				{
				noReset(1),
				reset(2)
				}
			ACCESS read-write
			STATUS mandatory
			DESCRIPTION
				"Reset modem statistics.
				1 = no effect
				2 = reset packet counters"
			::= { necEntry 15 }

		
		-- 1.3.6.1.4.1.3715.3.3.1.1.16
		necModemChnlDescTimeout OBJECT-TYPE
			SYNTAX Uint16 (0..600)
			ACCESS read-write
			STATUS mandatory
			DESCRIPTION
				"Timeout for CHNLDESC. Unit 1 second.
				
				This is the time the modem waits for a valid CHNLDESC message
				from the HMTS. If the timeout is exceeded, the modem starts
				scanning for another HMS data channel.
				
				Timeout value 0 means the modem will wait an infinite time
				if it has found a signal with sufficient level."
			::= { necEntry 16 }

		
		-- 1.3.6.1.4.1.3715.3.3.1.1.17
		necModemPollTimeout OBJECT-TYPE
			SYNTAX Uint16 (0..6000)
			ACCESS read-write
			STATUS mandatory
			DESCRIPTION
				"Timeout for unicast messages. Unit 1 second.
				
				This is the time the modem waits for any messages to its
				unicast MAC address. If the timeout is exceeded, the modem
				starts the registration process to inform the HMTS about
				it's presence.
				
				Timeout 0 will disable poll checking (contention mode operation)."
			::= { necEntry 17 }

		
		-- 1.3.6.1.4.1.3715.3.3.1.1.18
		necHwError OBJECT-TYPE
			SYNTAX INTEGER
				{
				hwOk(1),
				hwError(2)
				}
			ACCESS read-only
			STATUS mandatory
			DESCRIPTION
				"Module controller hardware status:
				1 = hardware OK
				2 = hardware error detected"
			::= { necEntry 18 }

		
		-- 1.3.6.1.4.1.3715.3.3.1.1.19
		necRxLevelStatus OBJECT-TYPE
			SYNTAX INTEGER
				{
				levelNormal(1),
				levelHIHI(2),
				levelHI(3),
				levelLO(4),
				levelLOLO(5)
				}
			ACCESS read-only
			STATUS mandatory
			DESCRIPTION
				"RF modem downstream receiver level status
				1 = normal
				3 = HI
				4 = LO"
			::= { necEntry 19 }

		
		-- 1.3.6.1.4.1.3715.3.3.1.1.20
		necTemperatureStatus OBJECT-TYPE
			SYNTAX INTEGER
				{
				tempNormal(1),
				tempHIHI(2),
				tempHI(3),
				tempLO(4),
				tempLOLO(5)
				}
			ACCESS read-only
			STATUS mandatory
			DESCRIPTION
				"Module temperature Status.
				1 = OK
				2 = HIHI
				3 = HI
				4 = LO
				5 = LOLO"
			::= { necEntry 20 }

		
-- bVrTable contains element specific information for
-- B amplifier (BKA603/803) modules in a BK
-- system.
-- 
-- Note that index is moduleIndex which is column in 
-- the moduleTable defined in TELESTE-COMMON-MIB. Rows in
-- this table exist only if there are corresponding
-- rows in the moduleTable.
-- 
		-- 1.3.6.1.4.1.3715.3.3.2
		bVrTable OBJECT-TYPE
			SYNTAX SEQUENCE OF BVrEntry
			ACCESS not-accessible
			STATUS mandatory
			DESCRIPTION
				"bVrTable contains element specific information for
				B amplifier (BKA603/803) modules in a BK system."
			::= { bkModules1 2 }

		
		-- 1.3.6.1.4.1.3715.3.3.2.1
		bVrEntry OBJECT-TYPE
			SYNTAX BVrEntry
			ACCESS not-accessible
			STATUS mandatory
			INDEX { moduleId }
			::= { bVrTable 1 }

		
		BVrEntry ::=
			SEQUENCE { 
				bVrGain
					Int16,
				bVrDetOffset
					Int16,
				bVrDetRefValue
					Int16,
				bVrDetOffsetHiHi
					Uint16,
				bVrDetOffsetHi
					Uint16,
				bVrDetOffsetLo
					Int16,
				bVrDetOffsetLoLo
					Int16,
				bVrDetOffsetDeadband
					Uint16,
				bVrDetRefMode
					INTEGER,
				bVrDetAverageMode
					INTEGER,
				bVrRfLevelStatus
					INTEGER,
				bVrTemperatureStatus
					INTEGER
			 }

		-- 1.3.6.1.4.1.3715.3.3.2.1.1
		bVrGain OBJECT-TYPE
			SYNTAX Int16 (-400..0)
			ACCESS read-write
			STATUS mandatory
			DESCRIPTION
				"Gain control value. Unit 0.01 dB.
				This object is implemented only with BKA803."
			::= { bVrEntry 1 }

		
		-- 1.3.6.1.4.1.3715.3.3.2.1.2
		bVrDetOffset OBJECT-TYPE
			SYNTAX Int16 (-10000..10000)
			ACCESS read-only
			STATUS mandatory
			DESCRIPTION
				"Broadband detector offset value, in reference to aAmpDetRefValue.
				Unit 0.01 dB."
			::= { bVrEntry 2 }

		
		-- 1.3.6.1.4.1.3715.3.3.2.1.3
		bVrDetRefValue OBJECT-TYPE
			SYNTAX Int16 (0..10000)
			ACCESS read-write
			STATUS mandatory
			DESCRIPTION
				"Broadband level detector reference. This is used
				as a reference point for limit values. Unit 0.01 dB."
			::= { bVrEntry 3 }

		
		-- 1.3.6.1.4.1.3715.3.3.2.1.4
		bVrDetOffsetHiHi OBJECT-TYPE
			SYNTAX Uint16 (0..10000)
			ACCESS read-write
			STATUS mandatory
			DESCRIPTION
				"Broadband detector offset high alarm limit. Unit 0.01 dB."
			::= { bVrEntry 4 }

		
		-- 1.3.6.1.4.1.3715.3.3.2.1.5
		bVrDetOffsetHi OBJECT-TYPE
			SYNTAX Uint16 (0..10000)
			ACCESS read-write
			STATUS mandatory
			DESCRIPTION
				"Broadband detector offset high warning limit. Unit 0.01 dB."
			::= { bVrEntry 5 }

		
		-- 1.3.6.1.4.1.3715.3.3.2.1.6
		bVrDetOffsetLo OBJECT-TYPE
			SYNTAX Int16 (-10000..0)
			ACCESS read-write
			STATUS mandatory
			DESCRIPTION
				"Broadband detector offset low warning limit. Unit 0.01 dB."
			::= { bVrEntry 6 }

		
		-- 1.3.6.1.4.1.3715.3.3.2.1.7
		bVrDetOffsetLoLo OBJECT-TYPE
			SYNTAX Int16 (-10000..0)
			ACCESS read-write
			STATUS mandatory
			DESCRIPTION
				"Broadband detector offset low alarm limit. Unit 0.01 dB."
			::= { bVrEntry 7 }

		
		-- 1.3.6.1.4.1.3715.3.3.2.1.8
		bVrDetOffsetDeadband OBJECT-TYPE
			SYNTAX Uint16 (50..1000)
			ACCESS read-write
			STATUS mandatory
			DESCRIPTION
				"Broadband detector offset deadband. Unit 0.01 dB."
			::= { bVrEntry 8 }

		
		-- 1.3.6.1.4.1.3715.3.3.2.1.9
		bVrDetRefMode OBJECT-TYPE
			SYNTAX INTEGER
				{
				refFactory(1),
				refCustom(2)
				}
			ACCESS read-write
			STATUS mandatory
			DESCRIPTION
				"Used broadband detector reference value:
				1 = factory set reference
				2 = custom reference"
			::= { bVrEntry 9 }

		
		-- 1.3.6.1.4.1.3715.3.3.2.1.10
		bVrDetAverageMode OBJECT-TYPE
			SYNTAX INTEGER
				{
				averagingOff(1),
				averagingOn(2)
				}
			ACCESS read-write
			STATUS mandatory
			DESCRIPTION
				"Broadband detector's averaging status:
				1 = averaging off
				2 = averaging on"
			::= { bVrEntry 10 }

		
		-- 1.3.6.1.4.1.3715.3.3.2.1.11
		bVrRfLevelStatus OBJECT-TYPE
			SYNTAX INTEGER
				{
				levelNormal(1),
				levelHIHI(2),
				levelHI(3),
				levelLO(4),
				levelLOLO(5)
				}
			ACCESS read-only
			STATUS mandatory
			DESCRIPTION
				"RF level status
				1 = OK
				2 = HIHI
				3 = HI
				4 = LO
				5 = LOLO"
			::= { bVrEntry 11 }

		
		-- 1.3.6.1.4.1.3715.3.3.2.1.12
		bVrTemperatureStatus OBJECT-TYPE
			SYNTAX INTEGER
				{
				tempNormal(1),
				tempHIHI(2),
				tempHI(3),
				tempLO(4),
				tempLOLO(5)
				}
			ACCESS read-only
			STATUS mandatory
			DESCRIPTION
				"Module temperature Status.
				1 = OK
				2 = HIHI
				3 = HI
				4 = LO
				5 = LOLO"
			::= { bVrEntry 12 }

		
-- cVrTable contains element specific information for
-- C amplifier (BKC629/829) modules in a BK
-- system.
-- 
-- Note that index is moduleIndex which is column in 
-- the moduleTable defined in TELESTE-COMMON-MIB. Rows in
-- this table exist only if there are corresponding
-- rows in the moduleTable.
-- 
		-- 1.3.6.1.4.1.3715.3.3.3
		cVrTable OBJECT-TYPE
			SYNTAX SEQUENCE OF CVrEntry
			ACCESS not-accessible
			STATUS mandatory
			DESCRIPTION
				"cVrTable contains element specific information for
				C amplifier (BKC629/829) modules in a BK system."
			::= { bkModules1 3 }

		
		-- 1.3.6.1.4.1.3715.3.3.3.1
		cVrEntry OBJECT-TYPE
			SYNTAX CVrEntry
			ACCESS not-accessible
			STATUS mandatory
			INDEX { moduleId }
			::= { cVrTable 1 }

		
		CVrEntry ::=
			SEQUENCE { 
				cVrGain
					Int16,
				cVrSlope
					Int16,
				cVrDetOffset
					Int16,
				cVrDetRefValue
					Int16,
				cVrDetOffsetHiHi
					Uint16,
				cVrDetOffsetHi
					Uint16,
				cVrDetOffsetLo
					Int16,
				cVrDetOffsetLoLo
					Int16,
				cVrDetOffsetDeadband
					Uint16,
				cVrDetRefMode
					INTEGER,
				cVrDetAverageMode
					INTEGER,
				cVrRfLevelStatus
					INTEGER,
				cVrTemperatureStatus
					INTEGER,
				cVrForwardFrequencyMode
					INTEGER,
				cVrReturnFrequencyMode
					INTEGER
			 }

		-- 1.3.6.1.4.1.3715.3.3.3.1.1
		cVrGain OBJECT-TYPE
			SYNTAX Int16 (-400..0)
			ACCESS read-write
			STATUS mandatory
			DESCRIPTION
				"Gain control value. Unit 0.01 dB.
				"
			::= { cVrEntry 1 }

		
		-- 1.3.6.1.4.1.3715.3.3.3.1.2
		cVrSlope OBJECT-TYPE
			SYNTAX Int16
				{
				slope0dB(1),
				slope3dB(2),
				slope6dB(3)
				}
			ACCESS read-write
			STATUS mandatory
			DESCRIPTION
				"High-end slope control.
				
				For BKC629 the value is enumerated:
				
				1 = 0 dB
				2 = -3 dB
				3 = -6 dB
				
				With older BKC829 modules, high-end slope control is continuous from
				0 to -6 dB. With 0.01 dB resolution the value range is thus 0 to -600.
				"
			::= { cVrEntry 2 }

		
		-- 1.3.6.1.4.1.3715.3.3.3.1.3
		cVrDetOffset OBJECT-TYPE
			SYNTAX Int16 (-10000..10000)
			ACCESS read-only
			STATUS mandatory
			DESCRIPTION
				"Broadband detector offset value, in reference to cAmpDetRefValue.
				Unit 0.01 dB."
			::= { cVrEntry 3 }

		
		-- 1.3.6.1.4.1.3715.3.3.3.1.4
		cVrDetRefValue OBJECT-TYPE
			SYNTAX Int16 (0..10000)
			ACCESS read-write
			STATUS mandatory
			DESCRIPTION
				"Broadband level detector reference. This is used as a reference
				point for limit values. Unit 0.01 dB."
			::= { cVrEntry 4 }

		
		-- 1.3.6.1.4.1.3715.3.3.3.1.5
		cVrDetOffsetHiHi OBJECT-TYPE
			SYNTAX Uint16 (0..10000)
			ACCESS read-write
			STATUS mandatory
			DESCRIPTION
				"Broadband detector offset high alarm limit. Unit 0.01 dB."
			::= { cVrEntry 5 }

		
		-- 1.3.6.1.4.1.3715.3.3.3.1.6
		cVrDetOffsetHi OBJECT-TYPE
			SYNTAX Uint16 (0..10000)
			ACCESS read-write
			STATUS mandatory
			DESCRIPTION
				"Broadband detector offset high warning limit. Unit 0.01 dB."
			::= { cVrEntry 6 }

		
		-- 1.3.6.1.4.1.3715.3.3.3.1.7
		cVrDetOffsetLo OBJECT-TYPE
			SYNTAX Int16 (-10000..0)
			ACCESS read-write
			STATUS mandatory
			DESCRIPTION
				"Broadband detector offset low warning limit. Unit 0.01 dB."
			::= { cVrEntry 7 }

		
		-- 1.3.6.1.4.1.3715.3.3.3.1.8
		cVrDetOffsetLoLo OBJECT-TYPE
			SYNTAX Int16 (-10000..0)
			ACCESS read-write
			STATUS mandatory
			DESCRIPTION
				"Broadband detector offset low alarm limit. Unit 0.01 dB."
			::= { cVrEntry 8 }

		
		-- 1.3.6.1.4.1.3715.3.3.3.1.9
		cVrDetOffsetDeadband OBJECT-TYPE
			SYNTAX Uint16 (50..1000)
			ACCESS read-write
			STATUS mandatory
			DESCRIPTION
				"Broadband detector offset deadband. Unit 0.01 dB."
			::= { cVrEntry 9 }

		
		-- 1.3.6.1.4.1.3715.3.3.3.1.10
		cVrDetRefMode OBJECT-TYPE
			SYNTAX INTEGER
				{
				refFactory(1),
				refCustom(2)
				}
			ACCESS read-write
			STATUS mandatory
			DESCRIPTION
				"Used broadband detector reference value:
				1 = factory set reference
				2 = custom reference"
			::= { cVrEntry 10 }

		
		-- 1.3.6.1.4.1.3715.3.3.3.1.11
		cVrDetAverageMode OBJECT-TYPE
			SYNTAX INTEGER
				{
				averagingOff(1),
				averagingOn(2)
				}
			ACCESS read-write
			STATUS mandatory
			DESCRIPTION
				"Broadband detector's averaging status:
				1 = averaging off
				2 = averaging on"
			::= { cVrEntry 11 }

		
		-- 1.3.6.1.4.1.3715.3.3.3.1.12
		cVrRfLevelStatus OBJECT-TYPE
			SYNTAX INTEGER
				{
				levelNormal(1),
				levelHIHI(2),
				levelHI(3),
				levelLO(4),
				levelLOLO(5)
				}
			ACCESS read-only
			STATUS mandatory
			DESCRIPTION
				"RF level status
				1 = OK
				2 = HIHI
				3 = HI
				4 = LO
				5 = LOLO"
			::= { cVrEntry 12 }

		
		-- 1.3.6.1.4.1.3715.3.3.3.1.13
		cVrTemperatureStatus OBJECT-TYPE
			SYNTAX INTEGER
				{
				tempNormal(1),
				tempHIHI(2),
				tempHI(3),
				tempLO(4),
				tempLOLO(5)
				}
			ACCESS read-only
			STATUS mandatory
			DESCRIPTION
				"Module temperature Status.
				1 = OK
				2 = HIHI
				3 = HI
				4 = LO
				5 = LOLO"
			::= { cVrEntry 13 }

		
		-- 1.3.6.1.4.1.3715.3.3.3.1.14
		cVrForwardFrequencyMode OBJECT-TYPE
			SYNTAX INTEGER
				{
				fwd862(1),
				fwd1g2(2)
				}
			ACCESS read-write
			STATUS mandatory
			DESCRIPTION
				"BKC670: Forward path mode:
				1 = 862 MHz
				2 = 1.2 GHz"
			::= { cVrEntry 14 }

		
		-- 1.3.6.1.4.1.3715.3.3.3.1.15
		cVrReturnFrequencyMode OBJECT-TYPE
			SYNTAX INTEGER
				{
				ret65(1),
				ret204(2)
				}
			ACCESS read-only
			STATUS mandatory
			DESCRIPTION
				"BKC670: Return path mode (detected diplexer):
				1 = 65 MHz
				2 = 204 MHz"
			::= { cVrEntry 15 }

		
-- rwSVrTable contains element specific information for
-- return amplifier (BKR100/200) modules in a BK
-- system.
-- 
-- Note that index is moduleIndex which is column in 
-- the moduleTable defined in TELESTE-COMMON-MIB. Rows in
-- this table exist only if there are corresponding
-- rows in the moduleTable.
-- 
		-- 1.3.6.1.4.1.3715.3.3.4
		rwSVrTable OBJECT-TYPE
			SYNTAX SEQUENCE OF RwSVrEntry
			ACCESS not-accessible
			STATUS mandatory
			DESCRIPTION
				"rwSVrTable contains element specific information for
				return amplifier (BKR100/200) modules in a BK system."
			::= { bkModules1 4 }

		
		-- 1.3.6.1.4.1.3715.3.3.4.1
		rwSVrEntry OBJECT-TYPE
			SYNTAX RwSVrEntry
			ACCESS not-accessible
			STATUS mandatory
			INDEX { moduleId }
			::= { rwSVrTable 1 }

		
		RwSVrEntry ::=
			SEQUENCE { 
				rwSVrGain
					Int16,
				rwSVrSlope
					Int16,
				rwSVrEqualiserType
					INTEGER,
				rwSVrGainSlopeMode
					INTEGER,
				rwSVrC1PortMode
					INTEGER,
				rwSVrC2PortMode
					INTEGER,
				rwSVrA1PortMode
					INTEGER,
				rwSVrA2PortMode
					INTEGER,
				rwSVrA3PortMode
					INTEGER,
				rwSVrNominalPortControl
					INTEGER,
				rwSVrPortStatus
					INTEGER,
				rwSVrTemperatureStatus
					INTEGER,
				rwSVrNotchControl
					INTEGER,
				rwSVrA4PortMode
					INTEGER,
				rwSVrFrequencyMode
					INTEGER
			 }

		-- 1.3.6.1.4.1.3715.3.3.4.1.1
		rwSVrGain OBJECT-TYPE
			SYNTAX Int16 (-800..0)
			ACCESS read-write
			STATUS mandatory
			DESCRIPTION
				"Gain control value. Unit 0.01 dB."
			::= { rwSVrEntry 1 }

		
		-- 1.3.6.1.4.1.3715.3.3.4.1.2
		rwSVrSlope OBJECT-TYPE
			SYNTAX Int16 (0..800)
			ACCESS read-write
			STATUS mandatory
			DESCRIPTION
				"Slope control value. Unit 0.01 dB."
			::= { rwSVrEntry 2 }

		
		-- 1.3.6.1.4.1.3715.3.3.4.1.3
		rwSVrEqualiserType OBJECT-TYPE
			SYNTAX INTEGER
				{
				eqTerm(0),
				eqBKE000(1),
				eqBKE040(2),
				eqBKE100(4),
				eqBKE160(6),
				eqBKE220(8),
				eqBKE280(10),
				eqBKE340(12),
				eqBKE400(14),
				eqBKE605(15),
				eqBKE610(16),
				eqBKE614(17),
				eqBKE618(18),
				eqBKE622(19),
				eqBKE626orBKZ070(20),
				eqBKE630orBKZ081(21),
				eqOTR(22),
				eqBKE634orBKZ092(23),
				eqBKE638orBKZ103(24),
				eqBKE642orBKZ114(25),
				eqOpen(26),
				eqNotDetected(27),
				eqOther(28),
				eqBKE14(100),
				eqBKE28(101),
				eqBKE42(102),
				eqBKE148(103),
				eqBKE288(104),
				eqBKE428(105),
				eqBKE003(113)
				}
			ACCESS read-write
			STATUS mandatory
			DESCRIPTION
				"Detected cable equaliser type indicator (from AVr):
				0  = Terminated
				1  = BKE000
				2  = BKE040
				4  = BKE100
				6  = BKE160
				8  = BKE220
				10 = BKE280
				12 = BKE340
				14 = BKE400
				15 = BKE605
				16 = BKE610
				17 = BKE614
				18 = BKE618
				19 = BKE622
				20 = BKE626 or BKZ070
				21 = BKE630 or BKZ081
				22 = OTR
				23 = BKE634 or BKZ092
				24 = BKE638 or BKZ103
				25 = BKE642 or BKZ114
				26 = Open
				27 = equaliser not detected
				28 = other equaliser type detected
				100 = BKE14
				101 = BKE28
				102 = BKE42
				103 = BKE148
				104 = BKE288
				105 = BKE428
				113 = BKE003
				Can be written only when rAmpGainSlopeMode is set to
				2 (= based on manual equaliser selection)."
			::= { rwSVrEntry 3 }

		
		-- 1.3.6.1.4.1.3715.3.3.4.1.4
		rwSVrGainSlopeMode OBJECT-TYPE
			SYNTAX INTEGER
				{
				controlManual(1),
				controlEquMan(2),
				controlEquAuto(3)
				}
			ACCESS read-write
			STATUS mandatory
			DESCRIPTION
				"Gain and slope control mode:
				1 = manual gain and slope control
				2 = based on manual equaliser selection
				3 = based on automatic equaliser selection."
			::= { rwSVrEntry 4 }

		
		-- 1.3.6.1.4.1.3715.3.3.4.1.5
		rwSVrC1PortMode OBJECT-TYPE
			SYNTAX INTEGER
				{
				inputOn(1),
				input6dB(2),
				input50dB(3),
				inputDisabled(4)
				}
			ACCESS read-write
			STATUS mandatory
			DESCRIPTION
				"BKR200: Port RC1 mode control:
				1 = 0 dB
				2 = - 6 dB
				3 = - 50 dB (off)
				
				BKR100: Port RC1 mode control:
				1 = 0 dB
				2 = - 6 dB
				3 = - 50 dB (off)
				4 = disabled (-50 dB without notification)"
			::= { rwSVrEntry 5 }

		
		-- 1.3.6.1.4.1.3715.3.3.4.1.6
		rwSVrC2PortMode OBJECT-TYPE
			SYNTAX INTEGER
				{
				inputOn(1),
				input6dB(2),
				input50dB(3),
				inputDisabled(4)
				}
			ACCESS read-write
			STATUS mandatory
			DESCRIPTION
				"BKR200: Port RC2 mode control:
				1 = 0 dB
				2 = - 6 dB
				3 = - 50 dB (off)
				
				BKR100: Port RC2 mode control:
				1 = 0 dB
				2 = - 6 dB
				3 = - 50 dB (off)
				4 = disabled (-50 dB without notification)"
			::= { rwSVrEntry 6 }

		
		-- 1.3.6.1.4.1.3715.3.3.4.1.7
		rwSVrA1PortMode OBJECT-TYPE
			SYNTAX INTEGER
				{
				inputOn(1),
				input6dB(2),
				input50dB(3)
				}
			ACCESS read-write
			STATUS mandatory
			DESCRIPTION
				"BKR200: Port RA1 mode control:
				1 = 0 dB
				2 = - 6 dB
				3 = - 50 dB
				
				BKR100: Port RA mode control:
				1 = 0 dB
				2 = - 6 dB"
			::= { rwSVrEntry 7 }

		
		-- 1.3.6.1.4.1.3715.3.3.4.1.8
		rwSVrA2PortMode OBJECT-TYPE
			SYNTAX INTEGER
				{
				inputOn(1),
				input6dB(2),
				input50dB(3)
				}
			ACCESS read-write
			STATUS mandatory
			DESCRIPTION
				"Port RA2 mode control:
				1 = 0 dB
				2 = - 6 dB
				3 = - 50 dB
				
				With BKR100 this object is read only. Returned value is
				always 3 (input50dB)."
			::= { rwSVrEntry 8 }

		
		-- 1.3.6.1.4.1.3715.3.3.4.1.9
		rwSVrA3PortMode OBJECT-TYPE
			SYNTAX INTEGER
				{
				inputOn(1),
				input6dB(2),
				input50dB(3)
				}
			ACCESS read-write
			STATUS mandatory
			DESCRIPTION
				"Port RA3 mode control:
				1 = 0 dB
				2 = - 6 dB
				3 = - 50 dB
				
				With BKR100 this object is read only. Returned value is
				always 3 (input50dB)."
			::= { rwSVrEntry 9 }

		
		-- 1.3.6.1.4.1.3715.3.3.4.1.10
		rwSVrNominalPortControl OBJECT-TYPE
			SYNTAX INTEGER
				{
				returnToNominal(1),
				defineAsNominal(2)
				}
			ACCESS read-write
			STATUS mandatory
			DESCRIPTION
				"This object controls the return path switches 'nominal'
				setting. Any combination of the switch positions can be
				defined as the 'nominal' setting. A reminder alarm
				will be initiated if any of the switches is not in it's
				nominal position.
				
				Set operations:
				1 = returnToNominal, returns all switches to their nominal
				    positions
				2 = defineNominal, stores the current port configuration
				    as the nominal configuration. 
				
				Get operations
				1 = all switches are in their nominal positions
				2 = one or more switches is not in it's nominal position
				
				Note: Immediately after a set (1 or 2), the return value 
				will be 1 meaning that the switches are in their nominal
				positions.
				
				With BKR100 this object is read only. Returned value is
				always 1 (returnToNominal)."
			::= { rwSVrEntry 10 }

		
		-- 1.3.6.1.4.1.3715.3.3.4.1.11
		rwSVrPortStatus OBJECT-TYPE
			SYNTAX INTEGER
				{
				portsNominal(1),
				portsNotNominal(2)
				}
			ACCESS read-only
			STATUS mandatory
			DESCRIPTION
				"Status of return path switches:
				1 = all switches are in their nominal positions
				2 = one or more switches is not in it's nominal position
				
				With BKR100 this object always returns 1 (portsNominal)."
			::= { rwSVrEntry 11 }

		
		-- 1.3.6.1.4.1.3715.3.3.4.1.12
		rwSVrTemperatureStatus OBJECT-TYPE
			SYNTAX INTEGER
				{
				tempNormal(1),
				tempHIHI(2),
				tempHI(3),
				tempLO(4),
				tempLOLO(5)
				}
			ACCESS read-only
			STATUS mandatory
			DESCRIPTION
				"Module temperature Status.
				1 = OK
				2 = HIHI
				3 = HI
				4 = LO
				5 = LOLO"
			::= { rwSVrEntry 12 }

		
		-- 1.3.6.1.4.1.3715.3.3.4.1.13
		rwSVrNotchControl OBJECT-TYPE
			SYNTAX INTEGER
				{
				notchDisable(1),
				notchEnable(2)
				}
			ACCESS read-write
			STATUS optional
			DESCRIPTION
				"Control of the 65 MHz notch in BKR300:
				1(notchDisable) = notch OFF
				2(notchEnable) = notch ON"
			::= { rwSVrEntry 13 }

		
		-- 1.3.6.1.4.1.3715.3.3.4.1.14
		rwSVrA4PortMode OBJECT-TYPE
			SYNTAX INTEGER
				{
				inputOn(1),
				input6dB(2),
				input50dB(3)
				}
			ACCESS read-write
			STATUS mandatory
			DESCRIPTION
				"BKR700: Port RA4 mode control:
				1 = 0 dB
				2 = - 6 dB
				3 = - 50 dB
				"
			::= { rwSVrEntry 14 }

		
		-- 1.3.6.1.4.1.3715.3.3.4.1.15
		rwSVrFrequencyMode OBJECT-TYPE
			SYNTAX INTEGER
				{
				ret65(1),
				ret204(2)
				}
			ACCESS read-write
			STATUS mandatory
			DESCRIPTION
				"BKR700: Return path mode:
				1 = 65 MHz
				2 = 204 MHz"
			::= { rwSVrEntry 15 }

		
-- aVrTable contains element specific information for
-- trunk amplifier (BKT60X/61X/80X) modules in a BK
-- system.
-- 
-- Note that index is moduleIndex which is column in 
-- the moduleTable defined in TELESTE-COMMON-MIB. Rows in
-- this table exist only if there are corresponding
-- rows in the moduleTable.
-- 
		-- 1.3.6.1.4.1.3715.3.3.5
		aVrTable OBJECT-TYPE
			SYNTAX SEQUENCE OF AVrEntry
			ACCESS not-accessible
			STATUS mandatory
			DESCRIPTION
				"aVrTable contains element specific information for
				trunk amplifier (BKT60X/61X/80X) modules in a BK system."
			::= { bkModules1 5 }

		
		-- 1.3.6.1.4.1.3715.3.3.5.1
		aVrEntry OBJECT-TYPE
			SYNTAX AVrEntry
			ACCESS not-accessible
			STATUS mandatory
			INDEX { moduleId }
			::= { aVrTable 1 }

		
		AVrEntry ::=
			SEQUENCE { 
				aVrGain
					Int16,
				aVrSlope
					Int16,
				aVrHighPilotLevel
					Uint16,
				aVrHighPilotTargetLevel
					Uint16,
				aVrHighPilotRefMode
					INTEGER,
				aVrHighPilotLevelHiHi
					Uint16,
				aVrHighPilotLevelHi
					Uint16,
				aVrHighPilotLevelLo
					Uint16,
				aVrHighPilotLevelLoLo
					Uint16,
				aVrHighPilotLevelDeadband
					Uint16,
				aVrAlscMode
					INTEGER,
				aVrAlscPilotLostMode
					INTEGER,
				aVrOperationMode
					INTEGER,
				aVrCurrentInput
					INTEGER,
				aVrMainEqualiserType
					INTEGER,
				aVrBackupEqualiserType
					INTEGER,
				aVrGainStatus
					INTEGER,
				aVrSlopeStatus
					INTEGER,
				aVrBackupStatus
					INTEGER,
				aVrHighPilotLevelStatus
					INTEGER,
				aVrTemperatureStatus
					INTEGER,
				aVrLowPilotLevel
					Uint16,
				aVrLowPilotTargetLevel
					Uint16,
				aVrLowPilotRefMode
					INTEGER,
				aVrLowPilotLevelHiHi
					Uint16,
				aVrLowPilotLevelHi
					Uint16,
				aVrLowPilotLevelLo
					Uint16,
				aVrLowPilotLevelLoLo
					Uint16,
				aVrLowPilotLevelDeadband
					Uint16,
				aVrLowPilotLevelStatus
					INTEGER,
				aVrAlscControlStatus
					INTEGER,
				aVrEqualiserStatus
					INTEGER,
				aVrAlscStatus
					INTEGER,
				aVrLowEndPeak
					INTEGER,
				aVrHighPilotFrequency
					Uint16,
				aVrLowPilotFrequency
					Uint16
			 }

		-- 1.3.6.1.4.1.3715.3.3.5.1.1
		aVrGain OBJECT-TYPE
			SYNTAX Int16 (-600..200)
			ACCESS read-write
			STATUS mandatory
			DESCRIPTION
				"Gain control value. Unit 0.01 dB"
			::= { aVrEntry 1 }

		
		-- 1.3.6.1.4.1.3715.3.3.5.1.2
		aVrSlope OBJECT-TYPE
			SYNTAX Int16 (-400..200)
			ACCESS read-write
			STATUS mandatory
			DESCRIPTION
				"Slope control value. Unit 0.01 dB."
			::= { aVrEntry 2 }

		
		-- 1.3.6.1.4.1.3715.3.3.5.1.3
		aVrHighPilotLevel OBJECT-TYPE
			SYNTAX Uint16 (0..12000)
			ACCESS read-only
			STATUS mandatory
			DESCRIPTION
				"Measured high pilot level. Unit 0.01 dBµV."
			::= { aVrEntry 3 }

		
		-- 1.3.6.1.4.1.3715.3.3.5.1.4
		aVrHighPilotTargetLevel OBJECT-TYPE
			SYNTAX Uint16 (0..10000)
			ACCESS read-write
			STATUS mandatory
			DESCRIPTION
				"High pilot target level. The ALSC system always
				tries to adjust gain and slope to set the pilot
				levels to target. Unit 0.01 dBµV."
			::= { aVrEntry 4 }

		
		-- 1.3.6.1.4.1.3715.3.3.5.1.5
		aVrHighPilotRefMode OBJECT-TYPE
			SYNTAX INTEGER
				{
				refFactory(1),
				refUser(2)
				}
			ACCESS read-write
			STATUS mandatory
			DESCRIPTION
				"High pilot level reference value in use:
				1 = factory set reference
				2 = custom reference"
			::= { aVrEntry 5 }

		
		-- 1.3.6.1.4.1.3715.3.3.5.1.6
		aVrHighPilotLevelHiHi OBJECT-TYPE
			SYNTAX Uint16 (0..10000)
			ACCESS read-write
			STATUS mandatory
			DESCRIPTION
				"High pilot level high alarm limit. Unit 0.01 dBµV."
			::= { aVrEntry 6 }

		
		-- 1.3.6.1.4.1.3715.3.3.5.1.7
		aVrHighPilotLevelHi OBJECT-TYPE
			SYNTAX Uint16 (0..10000)
			ACCESS read-write
			STATUS mandatory
			DESCRIPTION
				"High pilot level high warning limit. Unit 0.01 dBµV."
			::= { aVrEntry 7 }

		
		-- 1.3.6.1.4.1.3715.3.3.5.1.8
		aVrHighPilotLevelLo OBJECT-TYPE
			SYNTAX Uint16 (0..10000)
			ACCESS read-write
			STATUS mandatory
			DESCRIPTION
				"High pilot level low warning limit. Unit 0.01 dBµV."
			::= { aVrEntry 8 }

		
		-- 1.3.6.1.4.1.3715.3.3.5.1.9
		aVrHighPilotLevelLoLo OBJECT-TYPE
			SYNTAX Uint16 (0..10000)
			ACCESS read-write
			STATUS mandatory
			DESCRIPTION
				"High pilot level low alarm limit. Unit 0.01 dBµV."
			::= { aVrEntry 9 }

		
		-- 1.3.6.1.4.1.3715.3.3.5.1.10
		aVrHighPilotLevelDeadband OBJECT-TYPE
			SYNTAX Uint16 (50..1000)
			ACCESS read-write
			STATUS mandatory
			DESCRIPTION
				"High pilot level deadband. Unit 0.01 dBµV."
			::= { aVrEntry 10 }

		
		-- 1.3.6.1.4.1.3715.3.3.5.1.11
		aVrAlscMode OBJECT-TYPE
			SYNTAX INTEGER
				{
				alscOff(1),
				alscSinglePilot(2),
				alscDoublePilot(3)
				}
			ACCESS read-write
			STATUS mandatory
			DESCRIPTION
				"ALSC operating mode:
				1 = ALSC off
				2 = ALSC on, single pilot mode
				3 = ALSC on, double pilot mode
				"
			::= { aVrEntry 11 }

		
		-- 1.3.6.1.4.1.3715.3.3.5.1.12
		aVrAlscPilotLostMode OBJECT-TYPE
			SYNTAX INTEGER
				{
				alscFreeze(1),
				alscStart(2),
				alscFactory(3),
				alscUser(4)
				}
			ACCESS read-write
			STATUS mandatory
			DESCRIPTION
				"Gain and Slope control behaviour when the pilot
				is lost:
				1 = freeze to current positions
				2 = go to ALSC start settings
				3 = go to factory defaults
				4 = go to user defined settings"
			::= { aVrEntry 12 }

		
		-- 1.3.6.1.4.1.3715.3.3.5.1.13
		aVrOperationMode OBJECT-TYPE
			SYNTAX INTEGER
				{
				inputAutomatic(1),
				inputMain(2),
				inputBackup(3)
				}
			ACCESS read-write
			STATUS mandatory
			DESCRIPTION
				"Input switch operating mode:
				1 = automatic
				2 = main input
				3 = backup input"
			::= { aVrEntry 13 }

		
		-- 1.3.6.1.4.1.3715.3.3.5.1.14
		aVrCurrentInput OBJECT-TYPE
			SYNTAX INTEGER
				{
				inputMain(1),
				inputBackup(2)
				}
			ACCESS read-write
			STATUS mandatory
			DESCRIPTION
				"Currently selected input:
				1 = main input
				2 = backup input"
			::= { aVrEntry 14 }

		
		-- 1.3.6.1.4.1.3715.3.3.5.1.15
		aVrMainEqualiserType OBJECT-TYPE
			SYNTAX INTEGER
				{
				eqTerm(0),
				eqBKE000(1),
				eqBKE040(2),
				eqBKE100(4),
				eqBKE160(6),
				eqBKE220(8),
				eqBKE280(10),
				eqBKE340(12),
				eqBKE400(14),
				eqBKE605(15),
				eqBKE610(16),
				eqBKE614(17),
				eqBKE618(18),
				eqBKE622(19),
				eqBKE626orBKZ070(20),
				eqBKE630orBKZ081(21),
				eqOTR(22),
				eqBKE634orBKZ092(23),
				eqBKE638orBKZ103(24),
				eqBKE642orBKZ114(25),
				eqOpen(26),
				eqBKE14(100),
				eqBKE28(101),
				eqBKE42(102),
				eqBKE148(103),
				eqBKE288(104),
				eqBKE428(105),
				eqBKE003(113)
				}
			ACCESS read-only
			STATUS mandatory
			DESCRIPTION
				"Main input cable equaliser type indicator:
				0  = Terminated
				1  = BKE000
				2  = BKE040
				4  = BKE100
				6  = BKE160
				8  = BKE220
				10 = BKE280
				12 = BKE340
				14 = BKE400
				15 = BKE605
				16 = BKE610
				17 = BKE614
				18 = BKE618
				19 = BKE622
				20 = BKE626 or BKZ070
				21 = BKE630 or BKZ081
				22 = OTR
				23 = BKE634 or BKZ092
				24 = BKE638 or BKZ103
				25 = BKE642 or BKZ114
				26 = Open
				100 = BKE14
				101 = BKE28
				102 = BKE42
				103 = BKE148
				104 = BKE288
				105 = BKE428
				113 = BKE003"
			::= { aVrEntry 15 }

		
		-- 1.3.6.1.4.1.3715.3.3.5.1.16
		aVrBackupEqualiserType OBJECT-TYPE
			SYNTAX INTEGER
				{
				eqTerm(0),
				eqBKE000(1),
				eqBKE040(2),
				eqBKE100(4),
				eqBKE160(6),
				eqBKE220(8),
				eqBKE280(10),
				eqBKE340(12),
				eqBKE400(14),
				eqBKE605(15),
				eqBKE610(16),
				eqBKE614(17),
				eqBKE618(18),
				eqBKE622(19),
				eqBKE626orBKZ070(20),
				eqBKE630orBKZ081(21),
				eqOTR(22),
				eqBKE634orBKZ092(23),
				eqBKE638orBKZ103(24),
				eqBKE642orBKZ114(25),
				eqOpen(26)
				}
			ACCESS read-only
			STATUS mandatory
			DESCRIPTION
				"Backup input cable equaliser type indicator:
				0  = Terminated
				1  = BKE000
				2  = BKE040
				4  = BKE100
				6  = BKE160
				8  = BKE220
				10 = BKE280
				12 = BKE340
				14 = BKE400
				15 = BKE605
				16 = BKE610
				17 = BKE614
				18 = BKE618
				19 = BKE622
				20 = BKE626 or BKZ070
				21 = BKE630 or BKZ081
				22 = OTR
				23 = BKE634 or BKZ092
				24 = BKE638 or BKZ103
				25 = BKE642 or BKZ114
				26 = Open
				"
			::= { aVrEntry 16 }

		
		-- 1.3.6.1.4.1.3715.3.3.5.1.17
		aVrGainStatus OBJECT-TYPE
			SYNTAX INTEGER
				{
				gainNormal(1),
				gainMaximum(2),
				gainMinimum(3)
				}
			ACCESS read-only
			STATUS mandatory
			DESCRIPTION
				"Gain control status in ALSC mode:
				1 = normal
				2 = maximum
				3 = minimum
				"
			::= { aVrEntry 17 }

		
		-- 1.3.6.1.4.1.3715.3.3.5.1.18
		aVrSlopeStatus OBJECT-TYPE
			SYNTAX INTEGER
				{
				slopeNormal(1),
				slopeMaximum(2),
				slopeMinimum(3)
				}
			ACCESS read-only
			STATUS mandatory
			DESCRIPTION
				"Slope control status in ALSC mode:
				1 = normal
				2 = maximum
				3 = minimum
				"
			::= { aVrEntry 18 }

		
		-- 1.3.6.1.4.1.3715.3.3.5.1.19
		aVrBackupStatus OBJECT-TYPE
			SYNTAX INTEGER
				{
				backupInactive(1),
				backupActive(2)
				}
			ACCESS read-only
			STATUS mandatory
			DESCRIPTION
				"Backup input status:
				1 = backup input inactive
				2 = backup input active"
			::= { aVrEntry 19 }

		
		-- 1.3.6.1.4.1.3715.3.3.5.1.20
		aVrHighPilotLevelStatus OBJECT-TYPE
			SYNTAX INTEGER
				{
				levelNormal(1),
				levelHIHI(2),
				levelHI(3),
				levelLO(4),
				levelLOLO(5)
				}
			ACCESS read-only
			STATUS mandatory
			DESCRIPTION
				"High pilot level status:
				1 = OK
				2 = HIHI
				3 = HI
				4 = LO
				5 = LOLO"
			::= { aVrEntry 20 }

		
		-- 1.3.6.1.4.1.3715.3.3.5.1.21
		aVrTemperatureStatus OBJECT-TYPE
			SYNTAX INTEGER
				{
				tempNormal(1),
				tempHIHI(2),
				tempHI(3),
				tempLO(4),
				tempLOLO(5)
				}
			ACCESS read-only
			STATUS mandatory
			DESCRIPTION
				"Module temperature Status.
				1 = OK
				2 = HIHI
				3 = HI
				4 = LO
				5 = LOLO"
			::= { aVrEntry 21 }

		
		-- 1.3.6.1.4.1.3715.3.3.5.1.22
		aVrLowPilotLevel OBJECT-TYPE
			SYNTAX Uint16 (0..12000)
			ACCESS read-only
			STATUS optional
			DESCRIPTION
				"Measured low pilot level. Unit 0.01 dBµV."
			::= { aVrEntry 22 }

		
		-- 1.3.6.1.4.1.3715.3.3.5.1.23
		aVrLowPilotTargetLevel OBJECT-TYPE
			SYNTAX Uint16 (0..10000)
			ACCESS read-write
			STATUS optional
			DESCRIPTION
				"Low pilot target level. The ALSC system always
				tries to adjust gain and slope to set the pilot
				levels to target. Unit 0.01 dBµV."
			::= { aVrEntry 23 }

		
		-- 1.3.6.1.4.1.3715.3.3.5.1.24
		aVrLowPilotRefMode OBJECT-TYPE
			SYNTAX INTEGER
				{
				refFactory(1),
				refUser(2)
				}
			ACCESS read-write
			STATUS optional
			DESCRIPTION
				"Low pilot level reference value in use:
				1 = factory set reference
				2 = custom reference"
			::= { aVrEntry 24 }

		
		-- 1.3.6.1.4.1.3715.3.3.5.1.25
		aVrLowPilotLevelHiHi OBJECT-TYPE
			SYNTAX Uint16 (0..10000)
			ACCESS read-write
			STATUS optional
			DESCRIPTION
				"Low pilot level high alarm limit. Unit 0.01 dBµV."
			::= { aVrEntry 25 }

		
		-- 1.3.6.1.4.1.3715.3.3.5.1.26
		aVrLowPilotLevelHi OBJECT-TYPE
			SYNTAX Uint16 (0..10000)
			ACCESS read-write
			STATUS optional
			DESCRIPTION
				"Low pilot level high warning limit. Unit 0.01 dBµV."
			::= { aVrEntry 26 }

		
		-- 1.3.6.1.4.1.3715.3.3.5.1.27
		aVrLowPilotLevelLo OBJECT-TYPE
			SYNTAX Uint16 (0..10000)
			ACCESS read-write
			STATUS optional
			DESCRIPTION
				"Low pilot level low warning limit. Unit 0.01 dBµV."
			::= { aVrEntry 27 }

		
		-- 1.3.6.1.4.1.3715.3.3.5.1.28
		aVrLowPilotLevelLoLo OBJECT-TYPE
			SYNTAX Uint16 (0..10000)
			ACCESS read-write
			STATUS optional
			DESCRIPTION
				"Low pilot level low alarm limit. Unit 0.01 dBµV."
			::= { aVrEntry 28 }

		
		-- 1.3.6.1.4.1.3715.3.3.5.1.29
		aVrLowPilotLevelDeadband OBJECT-TYPE
			SYNTAX Uint16 (50..1000)
			ACCESS read-write
			STATUS optional
			DESCRIPTION
				"Low pilot level deadband. Unit 0.01 dBµV."
			::= { aVrEntry 29 }

		
		-- 1.3.6.1.4.1.3715.3.3.5.1.30
		aVrLowPilotLevelStatus OBJECT-TYPE
			SYNTAX INTEGER
				{
				levelNormal(1),
				levelHIHI(2),
				levelHI(3),
				levelLO(4),
				levelLOLO(5)
				}
			ACCESS read-only
			STATUS optional
			DESCRIPTION
				"Low pilot level status:
				1 = OK
				2 = HIHI
				3 = HI
				4 = LO
				5 = LOLO"
			::= { aVrEntry 30 }

		
		-- 1.3.6.1.4.1.3715.3.3.5.1.31
		aVrAlscControlStatus OBJECT-TYPE
			SYNTAX INTEGER
				{
				controlsNormal(1),
				controlsCloseToLimits(2)
				}
			ACCESS read-only
			STATUS optional
			DESCRIPTION
				"Status of ALSC controls:
				1 = Gain and slope controls are within normal operating
				    values
				2 = Gain or slope control is close to maximum/minimum
				    value
				"
			::= { aVrEntry 31 }

		
		-- 1.3.6.1.4.1.3715.3.3.5.1.32
		aVrEqualiserStatus OBJECT-TYPE
			SYNTAX INTEGER
				{
				eqDetNormal(1),
				eqDetFailure(2)
				}
			ACCESS read-only
			STATUS optional
			DESCRIPTION
				"Status of the equaliser detection cirsuit:
				1 = both equalisers are detected normally
				2 = one or both equalisers can not be detected
				"
			::= { aVrEntry 32 }

		
		-- 1.3.6.1.4.1.3715.3.3.5.1.33
		aVrAlscStatus OBJECT-TYPE
			SYNTAX INTEGER
				{
				alscNormal(1),
				alscSinglePilot(2)
				}
			ACCESS read-only
			STATUS optional
			DESCRIPTION
				"Double pilot ALSC status:
				1 = ALSC is working normally or is OFF
				2 = ALSC is in single pilot mode due to missing pilot
				    (slope control is frozen)
				
				"
			::= { aVrEntry 33 }

		
		-- 1.3.6.1.4.1.3715.3.3.5.1.34
		aVrLowEndPeak OBJECT-TYPE
			SYNTAX INTEGER
				{
				peakOff(1),
				peakOn(2)
				}
			ACCESS read-write
			STATUS mandatory
			DESCRIPTION
				"Control of the low end (85 MHz) peaking:
				1 = low end peak OFF (BKT690: 250 MHz peak on)
				2 = low end peak ON (BKT690: 85 MHz peak on)"
			::= { aVrEntry 34 }

		
		-- 1.3.6.1.4.1.3715.3.3.5.1.35
		aVrHighPilotFrequency OBJECT-TYPE
			SYNTAX Uint16 (0..12000)
			ACCESS read-write
			STATUS mandatory
			DESCRIPTION
				"BKT690: High pilot frequency. Unit 0.25 MHz."
			::= { aVrEntry 35 }

		
		-- 1.3.6.1.4.1.3715.3.3.5.1.36
		aVrLowPilotFrequency OBJECT-TYPE
			SYNTAX Uint16 (0..12000)
			ACCESS read-write
			STATUS mandatory
			DESCRIPTION
				"BKT690: Low pilot frequency. Unit 0.25 MHz."
			::= { aVrEntry 36 }

		
-- oTrTable contains element specific information for
-- optical transceiver (BKO900/BOX860) modules in a BK
-- system.
-- 
-- Note that index is moduleIndex which is column in 
-- the moduleTable defined in TELESTE-COMMON-MIB. Rows in
-- this table exist only if there are corresponding
-- rows in the moduleTable.
-- 
		-- 1.3.6.1.4.1.3715.3.3.6
		oTrTable OBJECT-TYPE
			SYNTAX SEQUENCE OF OTrEntry
			ACCESS not-accessible
			STATUS mandatory
			DESCRIPTION
				"oTrTable contains element specific information for
				optical transceiver (BKO900/BOX860) modules in a BK
				system."
			::= { bkModules1 6 }

		
		-- 1.3.6.1.4.1.3715.3.3.6.1
		oTrEntry OBJECT-TYPE
			SYNTAX OTrEntry
			ACCESS not-accessible
			STATUS mandatory
			INDEX { moduleId }
			::= { oTrTable 1 }

		
		OTrEntry ::=
			SEQUENCE { 
				oTrRxPower
					Int16,
				oTrRxPowerHiHi
					Int16,
				oTrRxPowerHi
					Int16,
				oTrRxPowerLo
					Int16,
				oTrRxPowerLoLo
					Int16,
				oTrRxPowerDeadband
					Uint16,
				oTrRxOutputState
					INTEGER,
				oTrRxOutputMode
					INTEGER,
				oTrRxRfOutDcSettings
					INTEGER,
				oTrTxPower
					Uint16,
				oTrTxPowerLo
					Int16,
				oTrTxPowerLoLo
					Int16,
				oTrTxPowerDeadband
					Uint16,
				oTrTxOmi
					Uint16,
				oTrTxFibreNumber
					INTEGER,
				oTrTxMode
					INTEGER,
				oTrTxPilotMode
					INTEGER,
				oTrTxInputState
					INTEGER,
				oTrTxInputMode
					INTEGER,
				oTrLaserCurrentRel
					Uint16,
				oTrLaserCurrentRelHi
					Uint16,
				oTrLaserCurrentRelDeadband
					Uint16,
				oTrActivity
					INTEGER,
				oTrMainReserveMode
					INTEGER,
				oTrCodeUsage
					INTEGER,
				oTrTxPilotStatus
					INTEGER,
				oTrLaserStatus
					INTEGER,
				oTrLinkStatus
					INTEGER,
				oTrRxInputPowerStatus
					INTEGER,
				oTrTxOutputPowerStatus
					INTEGER,
				oTrTxPowerHiHi
					Int16,
				oTrTxPowerHi
					Int16,
				oTrRxOutputLevelOffset
					INTEGER,
				oTrTxWavelength
					INTEGER,
				oTrTx2Power
					INTEGER,
				oTrTx2PowerLo
					INTEGER,
				oTrTx2PowerLoLo
					INTEGER,
				oTrTx2PowerDeadband
					INTEGER,
				oTrTx2Omi
					INTEGER,
				oTrTx2FibreNumber
					INTEGER,
				oTrTx2Mode
					INTEGER,
				oTrTx2PilotMode
					INTEGER,
				oTrTx2LaserCurrentRel
					INTEGER,
				oTrTx2LaserCurrentRelHi
					INTEGER,
				oTrTx2LaserCurrentRelDeadband
					INTEGER,
				oTrMainReserveMode2
					INTEGER,
				oTrCodeUsage2
					INTEGER,
				oTrTx2PilotStatus
					INTEGER,
				oTrTx2LaserStatus
					INTEGER,
				oTrTx2LinkStatus
					INTEGER,
				oTrTx2OutputPowerStatus
					INTEGER,
				oTrTx2PowerHiHi
					INTEGER,
				oTrTx2PowerHi
					INTEGER,
				oTrTx2Wavelength
					INTEGER,
				oTrTx21PortMode
					INTEGER,
				oTrTx22PortMode
					INTEGER,
				oTrNominalPortControl
					INTEGER,
				oTrRxGain
					INTEGER,
				oTrTx2Gain
					INTEGER
			 }

		-- 1.3.6.1.4.1.3715.3.3.6.1.1
		oTrRxPower OBJECT-TYPE
			SYNTAX Int16 (-2000..300)
			ACCESS read-only
			STATUS mandatory
			DESCRIPTION
				"Receiver input power. Unit 0.01 dBm."
			::= { oTrEntry 1 }

		
		-- 1.3.6.1.4.1.3715.3.3.6.1.2
		oTrRxPowerHiHi OBJECT-TYPE
			SYNTAX Int16 (-2000..300)
			ACCESS read-write
			STATUS mandatory
			DESCRIPTION
				"Receiver input power high alarm limit. Unit 0.01 dBm."
			::= { oTrEntry 2 }

		
		-- 1.3.6.1.4.1.3715.3.3.6.1.3
		oTrRxPowerHi OBJECT-TYPE
			SYNTAX Int16 (-2000..300)
			ACCESS read-write
			STATUS mandatory
			DESCRIPTION
				"Receiver input power high warning limit. Unit 0.01 dBm."
			::= { oTrEntry 3 }

		
		-- 1.3.6.1.4.1.3715.3.3.6.1.4
		oTrRxPowerLo OBJECT-TYPE
			SYNTAX Int16 (-2000..300)
			ACCESS read-write
			STATUS mandatory
			DESCRIPTION
				"Receiver input power low warning limit. Unit 0.01 dBm."
			::= { oTrEntry 4 }

		
		-- 1.3.6.1.4.1.3715.3.3.6.1.5
		oTrRxPowerLoLo OBJECT-TYPE
			SYNTAX Int16 (-2000..300)
			ACCESS read-write
			STATUS mandatory
			DESCRIPTION
				"Receiver input power low alarm limit. Unit 0.01 dBm."
			::= { oTrEntry 5 }

		
		-- 1.3.6.1.4.1.3715.3.3.6.1.6
		oTrRxPowerDeadband OBJECT-TYPE
			SYNTAX Uint16 (20..200)
			ACCESS read-write
			STATUS mandatory
			DESCRIPTION
				"Receiver input power deadband. Unit 0.01 dBm."
			::= { oTrEntry 6 }

		
		-- 1.3.6.1.4.1.3715.3.3.6.1.7
		oTrRxOutputState OBJECT-TYPE
			SYNTAX INTEGER
				{
				auxOff(1),
				bothOn(2),
				bothOff(3)
				}
			ACCESS read-only
			STATUS mandatory
			DESCRIPTION
				"Receiver output states:
				1 = aux (2) OFF
				2 = both ON
				3 = both OFF"
			::= { oTrEntry 7 }

		
		-- 1.3.6.1.4.1.3715.3.3.6.1.8
		oTrRxOutputMode OBJECT-TYPE
			SYNTAX INTEGER
				{
				auto(1),
				bothOn(2),
				auxOff(3),
				bothOff(4)
				}
			ACCESS read-write
			STATUS mandatory
			DESCRIPTION
				"Receiver output mode:
				1 = automatic control
				2 = both ON
				3 = aux OFF
				4 = both OFF
				
				Note: BOX860 does not support value 4 = both off."
			::= { oTrEntry 8 }

		
		-- 1.3.6.1.4.1.3715.3.3.6.1.9
		oTrRxRfOutDcSettings OBJECT-TYPE
			SYNTAX INTEGER
				{
				rxOutDcIgnore(1),
				rxOutDcUse(2)
				}
			ACCESS read-write
			STATUS optional
			DESCRIPTION
				"Output connector DC control voltage usage:
				1 = ignore DC voltage on output connector
				2 = use DC voltage (for controlling redundancy switching)"
			::= { oTrEntry 9 }

		
		-- 1.3.6.1.4.1.3715.3.3.6.1.10
		oTrTxPower OBJECT-TYPE
			SYNTAX Uint16 (0..600)
			ACCESS read-only
			STATUS mandatory
			DESCRIPTION
				"Transmitter output power. Unit 0.01 dBm."
			::= { oTrEntry 10 }

		
		-- 1.3.6.1.4.1.3715.3.3.6.1.11
		oTrTxPowerLo OBJECT-TYPE
			SYNTAX Int16 (-1000..1000)
			ACCESS read-write
			STATUS mandatory
			DESCRIPTION
				"Transmitter output power low warning limit. Unit 0.01 dBm."
			::= { oTrEntry 11 }

		
		-- 1.3.6.1.4.1.3715.3.3.6.1.12
		oTrTxPowerLoLo OBJECT-TYPE
			SYNTAX Int16 (-1000..1000)
			ACCESS read-write
			STATUS mandatory
			DESCRIPTION
				"Transmitter output power low alarm limit. Unit 0.01 dBm."
			::= { oTrEntry 12 }

		
		-- 1.3.6.1.4.1.3715.3.3.6.1.13
		oTrTxPowerDeadband OBJECT-TYPE
			SYNTAX Uint16 (20..200)
			ACCESS read-write
			STATUS mandatory
			DESCRIPTION
				"Transmitter output power deadband. Unit 0.01 dBm."
			::= { oTrEntry 13 }

		
		-- 1.3.6.1.4.1.3715.3.3.6.1.14
		oTrTxOmi OBJECT-TYPE
			SYNTAX Uint16 (350..1000)
			ACCESS read-write
			STATUS mandatory
			DESCRIPTION
				"Optical modulation index control value. Unit 0.01 %."
			::= { oTrEntry 14 }

		
		-- 1.3.6.1.4.1.3715.3.3.6.1.15
		oTrTxFibreNumber OBJECT-TYPE
			SYNTAX INTEGER (0..999)
			ACCESS read-write
			STATUS mandatory
			DESCRIPTION
				"Fibre node number. The transmitter sends the fibre node number
				with the pilot. At the receiver the number can be used to identify
				the correct fibre. Range 1...999, zero = no number entered."
			::= { oTrEntry 15 }

		
		-- 1.3.6.1.4.1.3715.3.3.6.1.16
		oTrTxMode OBJECT-TYPE
			SYNTAX INTEGER
				{
				txModeSleep(1),
				txModeNormal(2)
				}
			ACCESS read-write
			STATUS mandatory
			DESCRIPTION
				"Transmitter operating mode:
				1 = deep sleep mode (output power -6dB)
				2 = normal mode"
			::= { oTrEntry 16 }

		
		-- 1.3.6.1.4.1.3715.3.3.6.1.17
		oTrTxPilotMode OBJECT-TYPE
			SYNTAX INTEGER
				{
				pilotOff(1),
				pilotOn(2)
				}
			ACCESS read-write
			STATUS mandatory
			DESCRIPTION
				"Transmitter pilot mode:
				1 = Pilot off
				2 = Pilot on"
			::= { oTrEntry 17 }

		
		-- 1.3.6.1.4.1.3715.3.3.6.1.18
		oTrTxInputState OBJECT-TYPE
			SYNTAX INTEGER
				{
				auxOff(1),
				bothOn(2),
				bothOff(3)
				}
			ACCESS read-only
			STATUS mandatory
			DESCRIPTION
				"Transmitter input state:
				1 = aux (2) OFF
				2 = both ON
				3 = both OFF"
			::= { oTrEntry 18 }

		
		-- 1.3.6.1.4.1.3715.3.3.6.1.19
		oTrTxInputMode OBJECT-TYPE
			SYNTAX INTEGER
				{
				auto(1),
				bothOn(2),
				auxOff(3),
				bothOff(4)
				}
			ACCESS read-write
			STATUS mandatory
			DESCRIPTION
				"Transmitter input mode:
				1 = automatic control
				2 = both ON
				3 = aux OFF
				4 = both OFF"
			::= { oTrEntry 19 }

		
		-- 1.3.6.1.4.1.3715.3.3.6.1.20
		oTrLaserCurrentRel OBJECT-TYPE
			SYNTAX Uint16 (0..15000)
			ACCESS read-only
			STATUS mandatory
			DESCRIPTION
				"Laser current relative to factory set laser current.
				Unit 0.01 %."
			::= { oTrEntry 20 }

		
		-- 1.3.6.1.4.1.3715.3.3.6.1.21
		oTrLaserCurrentRelHi OBJECT-TYPE
			SYNTAX Uint16 (0..15000)
			ACCESS read-write
			STATUS mandatory
			DESCRIPTION
				"Relative laser current high warning limit. Unit 0.01 %."
			::= { oTrEntry 21 }

		
		-- 1.3.6.1.4.1.3715.3.3.6.1.22
		oTrLaserCurrentRelDeadband OBJECT-TYPE
			SYNTAX Uint16 (200..2000)
			ACCESS read-write
			STATUS mandatory
			DESCRIPTION
				"Relative laser current deadband. Unit 0.01 %."
			::= { oTrEntry 22 }

		
		-- 1.3.6.1.4.1.3715.3.3.6.1.23
		oTrActivity OBJECT-TYPE
			SYNTAX INTEGER
				{
				rxSleeping(1),
				rxActive(2)
				}
			ACCESS read-only
			STATUS optional
			DESCRIPTION
				"Module activity:
				1 = sleeping
				2 = active"
			::= { oTrEntry 23 }

		
		-- 1.3.6.1.4.1.3715.3.3.6.1.24
		oTrMainReserveMode OBJECT-TYPE
			SYNTAX INTEGER
				{
				modeReserve(1),
				modeMain(2)
				}
			ACCESS read-write
			STATUS mandatory
			DESCRIPTION
				"Role of the transceiver in 1+1 backup configuration:
				1 =  reserve unit (Default inactive)
				2 =  main unit (Default active)"
			::= { oTrEntry 24 }

		
		-- 1.3.6.1.4.1.3715.3.3.6.1.25
		oTrCodeUsage OBJECT-TYPE
			SYNTAX INTEGER
				{
				lineCodeInactive(1),
				lineCodeActive(2)
				}
			ACCESS read-write
			STATUS mandatory
			DESCRIPTION
				"Usage of the line codes:
				1 = line codes are not used
				2 = line codes are used
				Line codes are used to control backup switching in 1+1
				backup configuration."
			::= { oTrEntry 25 }

		
		-- 1.3.6.1.4.1.3715.3.3.6.1.26
		oTrTxPilotStatus OBJECT-TYPE
			SYNTAX INTEGER
				{
				pilotNormal(1),
				pilotFailure(2)
				}
			ACCESS read-only
			STATUS optional
			DESCRIPTION
				"Transmitter pilot generator status:
				1 = normal
				2 = pilot failure"
			::= { oTrEntry 26 }

		
		-- 1.3.6.1.4.1.3715.3.3.6.1.27
		oTrLaserStatus OBJECT-TYPE
			SYNTAX INTEGER
				{
				laserNormal(1),
				laserFailure(2)
				}
			ACCESS read-only
			STATUS mandatory
			DESCRIPTION
				"Laser status:
				1 = normal
				2 = failure"
			::= { oTrEntry 27 }

		
		-- 1.3.6.1.4.1.3715.3.3.6.1.28
		oTrLinkStatus OBJECT-TYPE
			SYNTAX INTEGER
				{
				linkNormal(1),
				linkReserveUnitActive(2),
				linkMainUnitSleeping(3)
				}
			ACCESS read-only
			STATUS mandatory
			DESCRIPTION
				"Link status:
				1 = normal
				2 = reserve unit is active
				3 = main unit is sleeping
				
				With BOX860 the meaning of value 2 depends on the unit
				configuration.
				
				Main unit: 2 = unit sleeping
				Reserve unit: 2 = unit active"
			::= { oTrEntry 28 }

		
		-- 1.3.6.1.4.1.3715.3.3.6.1.29
		oTrRxInputPowerStatus OBJECT-TYPE
			SYNTAX INTEGER
				{
				powerNormal(1),
				powerHIHI(2),
				powerHI(3),
				powerLO(4),
				powerLOLO(5)
				}
			ACCESS read-only
			STATUS mandatory
			DESCRIPTION
				"Optical input power status
				1 = OK
				2 = HIHI
				3 = HI
				4 = LO
				5 = LOLO"
			::= { oTrEntry 29 }

		
		-- 1.3.6.1.4.1.3715.3.3.6.1.30
		oTrTxOutputPowerStatus OBJECT-TYPE
			SYNTAX INTEGER
				{
				powerNormal(1),
				powerHIHI(2),
				powerHI(3),
				powerLO(4),
				powerLOLO(5)
				}
			ACCESS read-only
			STATUS mandatory
			DESCRIPTION
				"Optical output power status
				1 = OK
				2 = HIHI
				3 = HI
				4 = LO
				5 = LOLO"
			::= { oTrEntry 30 }

		
		-- 1.3.6.1.4.1.3715.3.3.6.1.31
		oTrTxPowerHiHi OBJECT-TYPE
			SYNTAX Int16 (-1000..1000)
			ACCESS read-write
			STATUS optional
			DESCRIPTION
				"Transmitter output power high alarm limit. Unit 0.01 dBm."
			::= { oTrEntry 31 }

		
		-- 1.3.6.1.4.1.3715.3.3.6.1.32
		oTrTxPowerHi OBJECT-TYPE
			SYNTAX Int16 (-1000..1000)
			ACCESS read-write
			STATUS optional
			DESCRIPTION
				"Transmitter output power high warning limit. Unit 0.01 dBm."
			::= { oTrEntry 32 }

		
		-- 1.3.6.1.4.1.3715.3.3.6.1.33
		oTrRxOutputLevelOffset OBJECT-TYPE
			SYNTAX INTEGER (-1250..1250)
			ACCESS read-write
			STATUS optional
			DESCRIPTION
				"Receiver output RF level offset. Unit 0.01 dB, 
				value range -1250...1250 (-12.5 dB to +12.5 dB)."
			::= { oTrEntry 33 }

		
		-- 1.3.6.1.4.1.3715.3.3.6.1.34
		oTrTxWavelength OBJECT-TYPE
			SYNTAX INTEGER
			ACCESS read-only
			STATUS optional
			DESCRIPTION
				"Transmitter optical wavelength. Unit 0.01 nm."
			::= { oTrEntry 34 }

		
		-- 1.3.6.1.4.1.3715.3.3.6.1.35
		oTrTx2Power OBJECT-TYPE
			SYNTAX INTEGER
			ACCESS read-only
			STATUS mandatory
			DESCRIPTION
				"Transmitter 2 output power. Unit 0.01 dBm."
			::= { oTrEntry 35 }

		
		-- 1.3.6.1.4.1.3715.3.3.6.1.36
		oTrTx2PowerLo OBJECT-TYPE
			SYNTAX INTEGER
			ACCESS read-write
			STATUS mandatory
			DESCRIPTION
				"Transmitter 2 output power low warning limit. Unit 0.01 dBm."
			::= { oTrEntry 36 }

		
		-- 1.3.6.1.4.1.3715.3.3.6.1.37
		oTrTx2PowerLoLo OBJECT-TYPE
			SYNTAX INTEGER
			ACCESS read-write
			STATUS mandatory
			DESCRIPTION
				"Transmitter 2 output power low alarm limit. Unit 0.01 dBm."
			::= { oTrEntry 37 }

		
		-- 1.3.6.1.4.1.3715.3.3.6.1.38
		oTrTx2PowerDeadband OBJECT-TYPE
			SYNTAX INTEGER
			ACCESS read-write
			STATUS mandatory
			DESCRIPTION
				"Transmitter 2 output power deadband. Unit 0.01 dBm."
			::= { oTrEntry 38 }

		
		-- 1.3.6.1.4.1.3715.3.3.6.1.39
		oTrTx2Omi OBJECT-TYPE
			SYNTAX INTEGER
			ACCESS read-write
			STATUS mandatory
			DESCRIPTION
				"Transmitter 2 optical modulation index control value. Unit 0.01 %.
				Depending on the unit and software version, this may be same than oTrTxOmi."
			::= { oTrEntry 39 }

		
		-- 1.3.6.1.4.1.3715.3.3.6.1.40
		oTrTx2FibreNumber OBJECT-TYPE
			SYNTAX INTEGER (0..999)
			ACCESS read-write
			STATUS mandatory
			DESCRIPTION
				"Transmitter 2 fibre node number. The transmitter sends the fibre node number
				with the pilot. At the receiver the number can be used to identify
				the correct fibre. Range 1...999, zero = no number entered."
			::= { oTrEntry 40 }

		
		-- 1.3.6.1.4.1.3715.3.3.6.1.41
		oTrTx2Mode OBJECT-TYPE
			SYNTAX INTEGER
				{
				txModeSleep(1),
				txModeNormal(2)
				}
			ACCESS read-write
			STATUS mandatory
			DESCRIPTION
				"Transmitter 2 operating mode:
				1 = deep sleep mode (output power -6dB)
				2 = normal mode"
			::= { oTrEntry 41 }

		
		-- 1.3.6.1.4.1.3715.3.3.6.1.42
		oTrTx2PilotMode OBJECT-TYPE
			SYNTAX INTEGER
				{
				pilotOff(1),
				pilotOn(2)
				}
			ACCESS read-write
			STATUS mandatory
			DESCRIPTION
				"Transmitter 2 pilot mode:
				1 = Pilot off
				2 = Pilot on"
			::= { oTrEntry 42 }

		
		-- 1.3.6.1.4.1.3715.3.3.6.1.43
		oTrTx2LaserCurrentRel OBJECT-TYPE
			SYNTAX INTEGER
			ACCESS read-only
			STATUS mandatory
			DESCRIPTION
				"Transmitter 2 laser current relative to factory set laser current. Unit 0.01 %."
			::= { oTrEntry 43 }

		
		-- 1.3.6.1.4.1.3715.3.3.6.1.44
		oTrTx2LaserCurrentRelHi OBJECT-TYPE
			SYNTAX INTEGER
			ACCESS read-write
			STATUS mandatory
			DESCRIPTION
				"Transmitter 2 relative laser current high warning limit. Unit 0.01 %."
			::= { oTrEntry 44 }

		
		-- 1.3.6.1.4.1.3715.3.3.6.1.45
		oTrTx2LaserCurrentRelDeadband OBJECT-TYPE
			SYNTAX INTEGER
			ACCESS read-write
			STATUS mandatory
			DESCRIPTION
				"Transmitter 2 relative laser current deadband. Unit 0.01 %."
			::= { oTrEntry 45 }

		
		-- 1.3.6.1.4.1.3715.3.3.6.1.46
		oTrMainReserveMode2 OBJECT-TYPE
			SYNTAX INTEGER
				{
				modeReserve(1),
				modeMain(2)
				}
			ACCESS read-write
			STATUS mandatory
			DESCRIPTION
				"Role of the transceiver 2 in 1+1 backup configuration:
				1 =  reserve unit (Default inactive)
				2 =  main unit (Default active)"
			::= { oTrEntry 46 }

		
		-- 1.3.6.1.4.1.3715.3.3.6.1.47
		oTrCodeUsage2 OBJECT-TYPE
			SYNTAX INTEGER
				{
				lineCodeInactive(1),
				lineCodeActive(2)
				}
			ACCESS read-write
			STATUS mandatory
			DESCRIPTION
				"Transmitter 2 usage of the line codes:
				1 = line codes are not used
				2 = line codes are used"
			::= { oTrEntry 47 }

		
		-- 1.3.6.1.4.1.3715.3.3.6.1.48
		oTrTx2PilotStatus OBJECT-TYPE
			SYNTAX INTEGER
				{
				pilotNormal(1),
				pilotFailure(2)
				}
			ACCESS read-only
			STATUS optional
			DESCRIPTION
				"Transmitter 2 pilot generator status:
				1 = normal
				2 = pilot failure"
			::= { oTrEntry 48 }

		
		-- 1.3.6.1.4.1.3715.3.3.6.1.49
		oTrTx2LaserStatus OBJECT-TYPE
			SYNTAX INTEGER
				{
				laserNormal(1),
				laserFailure(2)
				}
			ACCESS read-only
			STATUS mandatory
			DESCRIPTION
				"Trnasmitter 2 laser status:
				1 = normal
				2 = failure"
			::= { oTrEntry 49 }

		
		-- 1.3.6.1.4.1.3715.3.3.6.1.50
		oTrTx2LinkStatus OBJECT-TYPE
			SYNTAX INTEGER
				{
				linkNormal(1),
				linkReserveUnitActive(2),
				linkMainUnitSleeping(3)
				}
			ACCESS read-only
			STATUS mandatory
			DESCRIPTION
				"Transmitter 2 link status:
				1 = normal
				2 = reserve unit is active
				3 = main unit is sleeping"
			::= { oTrEntry 50 }

		
		-- 1.3.6.1.4.1.3715.3.3.6.1.51
		oTrTx2OutputPowerStatus OBJECT-TYPE
			SYNTAX INTEGER
				{
				powerNormal(1),
				powerHIHI(2),
				powerHI(3),
				powerLO(4),
				powerLOLO(5)
				}
			ACCESS read-only
			STATUS mandatory
			DESCRIPTION
				"Transmitter 2 optical output power status
				1 = OK
				2 = HIHI
				3 = HI
				4 = LO
				5 = LOLO"
			::= { oTrEntry 51 }

		
		-- 1.3.6.1.4.1.3715.3.3.6.1.52
		oTrTx2PowerHiHi OBJECT-TYPE
			SYNTAX INTEGER
			ACCESS read-write
			STATUS optional
			DESCRIPTION
				"Transmitter 2 output power high alarm limit. Unit 0.01 dBm."
			::= { oTrEntry 52 }

		
		-- 1.3.6.1.4.1.3715.3.3.6.1.53
		oTrTx2PowerHi OBJECT-TYPE
			SYNTAX INTEGER
			ACCESS read-write
			STATUS optional
			DESCRIPTION
				"Transmitter 2 output power high warning limit. Unit 0.01 dBm."
			::= { oTrEntry 53 }

		
		-- 1.3.6.1.4.1.3715.3.3.6.1.54
		oTrTx2Wavelength OBJECT-TYPE
			SYNTAX INTEGER
			ACCESS read-only
			STATUS optional
			DESCRIPTION
				"Transmitter 2 optical wavelength. Unit 0.01 nm."
			::= { oTrEntry 54 }

		
		-- 1.3.6.1.4.1.3715.3.3.6.1.56
		oTrTx21PortMode OBJECT-TYPE
			SYNTAX INTEGER
				{
				inputOn(1),
				input6dB(2),
				input50dB(3)
				}
			ACCESS read-write
			STATUS mandatory
			DESCRIPTION
				"Port Tx21 mode control:
				1 = 0 dB
				2 = - 6 dB
				3 = - 50 dB (off)"
			::= { oTrEntry 56 }

		
		-- 1.3.6.1.4.1.3715.3.3.6.1.57
		oTrTx22PortMode OBJECT-TYPE
			SYNTAX INTEGER
				{
				inputOn(1),
				input6dB(2),
				input50dB(3)
				}
			ACCESS read-write
			STATUS mandatory
			DESCRIPTION
				"Port Tx22 mode control:
				1 = 0 dB
				2 = - 6 dB
				3 = - 50 dB (off)"
			::= { oTrEntry 57 }

		
		-- 1.3.6.1.4.1.3715.3.3.6.1.58
		oTrNominalPortControl OBJECT-TYPE
			SYNTAX INTEGER
				{
				returnToNominal(1),
				defineAsNominal(2)
				}
			ACCESS read-write
			STATUS mandatory
			DESCRIPTION
				"This object controls the return path switches 'nominal'
				setting. Any combination of the switch positions can be
				defined as the 'nominal' setting. Alarm is activated if
				any of the switches is not in its nominal position.
				
				Set operations:
				1 = returnToNominal, returns all switches to their nominal positions
				2 = defineNominal, stores the current port configuration as the nominal configuration. 
				
				Get operations
				1 = all switches are in their nominal positions
				2 = one or more switches is not in it's nominal position"
			::= { oTrEntry 58 }

		
		-- 1.3.6.1.4.1.3715.3.3.6.1.59
		oTrRxGain OBJECT-TYPE
			SYNTAX INTEGER
			ACCESS read-write
			STATUS mandatory
			DESCRIPTION
				"Receiver gain control value. Unit 0.01 dB."
			::= { oTrEntry 59 }

		
		-- 1.3.6.1.4.1.3715.3.3.6.1.60
		oTrTx2Gain OBJECT-TYPE
			SYNTAX INTEGER
			ACCESS read-write
			STATUS mandatory
			DESCRIPTION
				"Transmitter 2 gain control value. Unit 0.01 dB."
			::= { oTrEntry 60 }

		
-- oRxTable contains element specific information for
-- optical receiver (BOR1000) modules in a BK
-- system.
-- 
-- Note that index is moduleIndex which is column in 
-- the moduleTable defined in TELESTE-COMMON-MIB. Rows in
-- this table exist only if there are corresponding
-- rows in the moduleTable.
-- 
		-- 1.3.6.1.4.1.3715.3.3.7
		oRxTable OBJECT-TYPE
			SYNTAX SEQUENCE OF ORxEntry
			ACCESS not-accessible
			STATUS mandatory
			DESCRIPTION
				"oRxTable contains element specific information for
				optical receiver (BOR1000) modules in a BK system."
			::= { bkModules1 7 }

		
		-- 1.3.6.1.4.1.3715.3.3.7.1
		oRxEntry OBJECT-TYPE
			SYNTAX ORxEntry
			ACCESS not-accessible
			STATUS mandatory
			INDEX { moduleId }
			::= { oRxTable 1 }

		
		ORxEntry ::=
			SEQUENCE { 
				oRxInputPower
					Int16,
				oRxInputPowerHiHi
					Int16,
				oRxInputPowerHi
					Int16,
				oRxInputPowerLo
					Int16,
				oRxInputPowerLoLo
					Int16,
				oRxInputPowerDeadband
					Uint16,
				oRxActivity
					INTEGER,
				oRxInputPowerStatus
					INTEGER,
				oRxOutputLevelOffset
					INTEGER
			 }

		-- 1.3.6.1.4.1.3715.3.3.7.1.1
		oRxInputPower OBJECT-TYPE
			SYNTAX Int16 (-2000..300)
			ACCESS read-only
			STATUS mandatory
			DESCRIPTION
				"Optical input power. Unit 0.01 dBm."
			::= { oRxEntry 1 }

		
		-- 1.3.6.1.4.1.3715.3.3.7.1.2
		oRxInputPowerHiHi OBJECT-TYPE
			SYNTAX Int16 (-2000..300)
			ACCESS read-write
			STATUS mandatory
			DESCRIPTION
				"Optical input power high alarm limit. Unit 0.01 dBm."
			::= { oRxEntry 2 }

		
		-- 1.3.6.1.4.1.3715.3.3.7.1.3
		oRxInputPowerHi OBJECT-TYPE
			SYNTAX Int16 (-2000..300)
			ACCESS read-write
			STATUS mandatory
			DESCRIPTION
				"Optical input power high warning limit. Unit 0.01 dBm."
			::= { oRxEntry 3 }

		
		-- 1.3.6.1.4.1.3715.3.3.7.1.4
		oRxInputPowerLo OBJECT-TYPE
			SYNTAX Int16 (-2000..300)
			ACCESS read-write
			STATUS mandatory
			DESCRIPTION
				"Optical input power low warning limit. Unit 0.01 dBm."
			::= { oRxEntry 4 }

		
		-- 1.3.6.1.4.1.3715.3.3.7.1.5
		oRxInputPowerLoLo OBJECT-TYPE
			SYNTAX Int16 (-2000..300)
			ACCESS read-write
			STATUS mandatory
			DESCRIPTION
				"Optical input power low alarm limit. Unit 0.01 dBm."
			::= { oRxEntry 5 }

		
		-- 1.3.6.1.4.1.3715.3.3.7.1.6
		oRxInputPowerDeadband OBJECT-TYPE
			SYNTAX Uint16 (20..200)
			ACCESS read-write
			STATUS mandatory
			DESCRIPTION
				"Optical input power deadband. Unit 0.01 dBm."
			::= { oRxEntry 6 }

		
		-- 1.3.6.1.4.1.3715.3.3.7.1.7
		oRxActivity OBJECT-TYPE
			SYNTAX INTEGER
				{
				rxSleeping(1),
				rxActive(2)
				}
			ACCESS read-only
			STATUS optional
			DESCRIPTION
				"Receiver activity:
				1 = sleeping
				2 = active"
			::= { oRxEntry 7 }

		
		-- 1.3.6.1.4.1.3715.3.3.7.1.8
		oRxInputPowerStatus OBJECT-TYPE
			SYNTAX INTEGER
				{
				powerNormal(1),
				powerHIHI(2),
				powerHI(3),
				powerLO(4),
				powerLOLO(5)
				}
			ACCESS read-only
			STATUS mandatory
			DESCRIPTION
				"Optical input power status
				1 = OK
				2 = HIHI
				3 = HI
				4 = LO
				5 = LOLO"
			::= { oRxEntry 8 }

		
		-- 1.3.6.1.4.1.3715.3.3.7.1.9
		oRxOutputLevelOffset OBJECT-TYPE
			SYNTAX INTEGER (-1250..1250)
			ACCESS read-write
			STATUS optional
			DESCRIPTION
				"Output RF level offset. Unit 0.01 dB, 
				value range -1250...1250 (-12.5 dB to +12.5 dB)."
			::= { oRxEntry 9 }

		
-- sEqTable contains element specific information for
-- System Equaliser (BKE90X) modules in a BK system.
-- 
-- Note that index is moduleIndex which is column in 
-- the moduleTable defined in TELESTE-COMMON-MIB. Rows in
-- this table exist only if there are corresponding
-- rows in the moduleTable.
		-- 1.3.6.1.4.1.3715.3.3.10
		sEqTable OBJECT-TYPE
			SYNTAX SEQUENCE OF SEqEntry
			ACCESS not-accessible
			STATUS mandatory
			DESCRIPTION
				"sEqTable contains element specific information for
				System Equaliser (BKE90X) modules in a BK system."
			::= { bkModules1 10 }

		
		-- 1.3.6.1.4.1.3715.3.3.10.1
		sEqEntry OBJECT-TYPE
			SYNTAX SEqEntry
			ACCESS not-accessible
			STATUS mandatory
			INDEX { moduleId }
			::= { sEqTable 1 }

		
		SEqEntry ::=
			SEQUENCE { 
				sEqControl
					INTEGER,
				sEqGain
					INTEGER,
				sEqCableCurve
					INTEGER,
				sEqPeak1Gain
					INTEGER,
				sEqPeak2Frequency
					INTEGER,
				sEqPeak2Gain
					INTEGER,
				sEqNotch1Frequency
					INTEGER,
				sEqNotch1Gain
					INTEGER,
				sEqNotch2Frequency
					INTEGER,
				sEqNotch2Gain
					INTEGER,
				sEqPeak3Gain
					INTEGER,
				sEqStatus
					INTEGER,
				sEqPeak4Frequency
					INTEGER,
				sEqPeak4Gain
					INTEGER,
				sEqNetworkType
					INTEGER,
				sEqNotch2FreqRange
					INTEGER
			 }

		-- 1.3.6.1.4.1.3715.3.3.10.1.1
		sEqControl OBJECT-TYPE
			SYNTAX INTEGER
				{
				storeAsNominal(1),
				revertToNominal(2),
				revertToFlat(3)
				}
			ACCESS read-write
			STATUS mandatory
			DESCRIPTION
				"Equaliser common control:
				1 = store current settings as nominal setting
				2 = revert to nominal settings
				3 = revert to flat settings"
			::= { sEqEntry 1 }

		
		-- 1.3.6.1.4.1.3715.3.3.10.1.2
		sEqGain OBJECT-TYPE
			SYNTAX INTEGER (-400..150)
			ACCESS read-write
			STATUS mandatory
			DESCRIPTION
				"Flat gain/attenuation of the module. Unit 0.01 dB."
			::= { sEqEntry 2 }

		
		-- 1.3.6.1.4.1.3715.3.3.10.1.3
		sEqCableCurve OBJECT-TYPE
			SYNTAX INTEGER (-120..120)
			ACCESS read-write
			STATUS mandatory
			DESCRIPTION
				"Cable curve correction value. Unit 0.01 dB."
			::= { sEqEntry 3 }

		
		-- 1.3.6.1.4.1.3715.3.3.10.1.4
		sEqPeak1Gain OBJECT-TYPE
			SYNTAX INTEGER (0..140)
			ACCESS read-write
			STATUS mandatory
			DESCRIPTION
				"Gain/attenuation value of low band edge (85 MHz) equaliser. Unit 0.01 dB.
				- BKE900/BKE901: 0 dB/1 dB
				- BKE902: 0 dB/1.4 dB
				"
			::= { sEqEntry 4 }

		
		-- 1.3.6.1.4.1.3715.3.3.10.1.5
		sEqPeak2Frequency OBJECT-TYPE
			SYNTAX INTEGER (1300..3000)
			ACCESS read-write
			STATUS mandatory
			DESCRIPTION
				"Centre frequency of peak equaliser 2. Unit 0.1 MHz.
				Product specific adjustment ranges:
				- BKE900: 130...160 MHz
				- BKE901/BKE902: 130...300 MHz"
			::= { sEqEntry 5 }

		
		-- 1.3.6.1.4.1.3715.3.3.10.1.6
		sEqPeak2Gain OBJECT-TYPE
			SYNTAX INTEGER (0..160)
			ACCESS read-write
			STATUS mandatory
			DESCRIPTION
				"Gain/attenuation value of peak equaliser 2. Unit 0.01 dB."
			::= { sEqEntry 6 }

		
		-- 1.3.6.1.4.1.3715.3.3.10.1.7
		sEqNotch1Frequency OBJECT-TYPE
			SYNTAX INTEGER (2200..2800)
			ACCESS read-write
			STATUS mandatory
			DESCRIPTION
				"Centre frequency of notch equaliser 1. Unit 0.1 MHz."
			::= { sEqEntry 7 }

		
		-- 1.3.6.1.4.1.3715.3.3.10.1.8
		sEqNotch1Gain OBJECT-TYPE
			SYNTAX INTEGER (-100..0)
			ACCESS read-write
			STATUS mandatory
			DESCRIPTION
				"Gain/attenuation value of notch equaliser 1. Unit 0.01 dB."
			::= { sEqEntry 8 }

		
		-- 1.3.6.1.4.1.3715.3.3.10.1.9
		sEqNotch2Frequency OBJECT-TYPE
			SYNTAX INTEGER (4000..5200)
			ACCESS read-write
			STATUS mandatory
			DESCRIPTION
				"Centre frequency of notch equaliser 1. Unit 0.1 MHz.
				Product specific adjustment ranges:
				- BKE900: 400...450 MHz
				- BKE901: 400...470 MHz
				- BKE901 G02Ä00/BKE902: 450...520 MHz"
			::= { sEqEntry 9 }

		
		-- 1.3.6.1.4.1.3715.3.3.10.1.10
		sEqNotch2Gain OBJECT-TYPE
			SYNTAX INTEGER (-140..0)
			ACCESS read-write
			STATUS mandatory
			DESCRIPTION
				"Gain/attenuation value of notch equaliser 2. Unit 0.01 dB.
				"
			::= { sEqEntry 10 }

		
		-- 1.3.6.1.4.1.3715.3.3.10.1.11
		sEqPeak3Gain OBJECT-TYPE
			SYNTAX INTEGER (0..150)
			ACCESS read-write
			STATUS mandatory
			DESCRIPTION
				"Gain/attenuation value of peak equaliser 3. Unit 0.01 dB.
				Product specific fixed centre frequency:
				- BKE900: 555 MHz
				- BKE901: 511 MHz
				- BKE902: 170 MHz"
			::= { sEqEntry 11 }

		
		-- 1.3.6.1.4.1.3715.3.3.10.1.12
		sEqStatus OBJECT-TYPE
			SYNTAX INTEGER
				{
				nominal(1),
				notNominal(2)
				}
			ACCESS read-only
			STATUS mandatory
			DESCRIPTION
				"Equaliser status:
				1 = settings in nominal state
				2 = settings not in nominal state
				This object has an entry in the discretePropertyTable."
			::= { sEqEntry 12 }

		
		-- 1.3.6.1.4.1.3715.3.3.10.1.13
		sEqPeak4Frequency OBJECT-TYPE
			SYNTAX INTEGER (6800..8600)
			ACCESS read-write
			STATUS mandatory
			DESCRIPTION
				"Centre frequency of peak equaliser 4. Unit 0.1 MHz.
				Available only with BKE901 and BKE902."
			::= { sEqEntry 13 }

		
		-- 1.3.6.1.4.1.3715.3.3.10.1.14
		sEqPeak4Gain OBJECT-TYPE
			SYNTAX INTEGER (0..160)
			ACCESS read-write
			STATUS mandatory
			DESCRIPTION
				"Gain/attenuation value of peak equaliser 4. Unit 0.01 dB.
				Available only with BKE901 and BKE902."
			::= { sEqEntry 14 }

		
		-- 1.3.6.1.4.1.3715.3.3.10.1.15
		sEqNetworkType OBJECT-TYPE
			SYNTAX INTEGER
				{
				bkt601and612and604(1),
				bkt612and605(2),
				bkt605(3)
				}
			ACCESS read-write
			STATUS mandatory
			DESCRIPTION
				"Type of network where BKE901/BKE902 is used:
				1 = BKT601/BKT612/BKT604
				2 = BKT612/BKT605
				3 = BKT605"
			::= { sEqEntry 15 }

		
		-- 1.3.6.1.4.1.3715.3.3.10.1.16
		sEqNotch2FreqRange OBJECT-TYPE
			SYNTAX INTEGER
				{
				oldRange(0),
				newRange(1)
				}
			ACCESS read-only
			STATUS mandatory
			DESCRIPTION
				"Notch equaliser 2 frequency range:
				0 = old range (400...470 MHz)
				1 = new range (450...520 MHz)"
			::= { sEqEntry 16 }

		
-- strVGtTable contains element specific information for
-- power supply (BKP065) modules in a BK system.
-- 
-- Note that index is moduleIndex which is column in 
-- the moduleTable defined in TELESTE-COMMON-MIB. Rows in
-- this table exist only if there are corresponding
-- rows in the moduleTable.
-- 
		-- 1.3.6.1.4.1.3715.3.3.11
		strVGtTable OBJECT-TYPE
			SYNTAX SEQUENCE OF StrVGtEntry
			ACCESS not-accessible
			STATUS mandatory
			DESCRIPTION
				"strVGtTable contains element specific information for
				power supply (BKP065) modules in a BK system."
			::= { bkModules1 11 }

		
		-- 1.3.6.1.4.1.3715.3.3.11.1
		strVGtEntry OBJECT-TYPE
			SYNTAX StrVGtEntry
			ACCESS not-accessible
			STATUS mandatory
			INDEX { moduleId }
			::= { strVGtTable 1 }

		
		StrVGtEntry ::=
			SEQUENCE { 
				strVGtInputVoltage
					INTEGER,
				strVGtInputCurrent
					INTEGER,
				strVGtOutputVoltage
					INTEGER,
				strVGtOutputCurrent
					INTEGER,
				strVGtInputVoltageStatus
					INTEGER,
				strVGtOutputVoltageStatus
					INTEGER,
				strVGtOutputCurrentStatus
					INTEGER,
				strVGtTemperatureStatus
					INTEGER,
				strVGtLastPacketTime
					INTEGER,
				strVGtInternalData
					OCTET STRING
			 }

		-- 1.3.6.1.4.1.3715.3.3.11.1.1
		strVGtInputVoltage OBJECT-TYPE
			SYNTAX INTEGER
			ACCESS read-only
			STATUS mandatory
			DESCRIPTION
				"Measured input voltage, RMS value. Unit 0.01 V."
			::= { strVGtEntry 1 }

		
		-- 1.3.6.1.4.1.3715.3.3.11.1.2
		strVGtInputCurrent OBJECT-TYPE
			SYNTAX INTEGER
			ACCESS read-only
			STATUS mandatory
			DESCRIPTION
				"Calculated/estimated input current, RMS value. Unit 0.01 A."
			::= { strVGtEntry 2 }

		
		-- 1.3.6.1.4.1.3715.3.3.11.1.3
		strVGtOutputVoltage OBJECT-TYPE
			SYNTAX INTEGER
			ACCESS read-only
			STATUS mandatory
			DESCRIPTION
				"Measured output voltage, DC value. Unit 0.01 V."
			::= { strVGtEntry 3 }

		
		-- 1.3.6.1.4.1.3715.3.3.11.1.4
		strVGtOutputCurrent OBJECT-TYPE
			SYNTAX INTEGER
			ACCESS read-only
			STATUS mandatory
			DESCRIPTION
				"Measured output current, DC value. Unit 0.01 A."
			::= { strVGtEntry 4 }

		
		-- 1.3.6.1.4.1.3715.3.3.11.1.11
		strVGtInputVoltageStatus OBJECT-TYPE
			SYNTAX INTEGER
				{
				voltageNormal(1),
				voltageHIHI(2),
				voltageHI(3),
				voltageLO(4),
				voltageLOLO(5)
				}
			ACCESS read-only
			STATUS mandatory
			DESCRIPTION
				"Input voltage status
				1 = OK
				2 = HIHI
				3 = HI
				4 = LO
				5 = LOLO"
			::= { strVGtEntry 11 }

		
		-- 1.3.6.1.4.1.3715.3.3.11.1.13
		strVGtOutputVoltageStatus OBJECT-TYPE
			SYNTAX INTEGER
				{
				voltageNormal(1),
				voltageHIHI(2),
				voltageHI(3),
				voltageLO(4),
				voltageLOLO(5)
				}
			ACCESS read-only
			STATUS mandatory
			DESCRIPTION
				"Output voltage status
				1 = OK
				2 = HIHI
				3 = HI
				4 = LO
				5 = LOLO"
			::= { strVGtEntry 13 }

		
		-- 1.3.6.1.4.1.3715.3.3.11.1.14
		strVGtOutputCurrentStatus OBJECT-TYPE
			SYNTAX INTEGER
				{
				currentNormal(1),
				currentHIHI(2),
				currentHI(3),
				currentLO(4),
				currentLOLO(5)
				}
			ACCESS read-only
			STATUS mandatory
			DESCRIPTION
				"Output current status
				1 = OK
				2 = HIHI
				3 = HI
				4 = LO
				5 = LOLO"
			::= { strVGtEntry 14 }

		
		-- 1.3.6.1.4.1.3715.3.3.11.1.15
		strVGtTemperatureStatus OBJECT-TYPE
			SYNTAX INTEGER
				{
				tempNormal(1),
				tempHIHI(2),
				tempHI(3),
				tempLO(4),
				tempLOLO(5)
				}
			ACCESS read-only
			STATUS mandatory
			DESCRIPTION
				"Module temperature status.
				1 = OK
				2 = HIHI
				3 = HI
				4 = LO
				5 = LOLO"
			::= { strVGtEntry 15 }

		
		-- 1.3.6.1.4.1.3715.3.3.11.1.20
		strVGtLastPacketTime OBJECT-TYPE
			SYNTAX INTEGER
			ACCESS read-only
			STATUS mandatory
			DESCRIPTION
				"Time since last valid data packet from power supply. Unit 1 s."
			::= { strVGtEntry 20 }

		
		-- 1.3.6.1.4.1.3715.3.3.11.1.100
		strVGtInternalData OBJECT-TYPE
			SYNTAX OCTET STRING (SIZE (0..200))
			ACCESS read-only
			STATUS mandatory
			DESCRIPTION
				"Copy of the binary data packet contents sent by the power supply."
			::= { strVGtEntry 100 }

		
		-- 1.3.6.1.4.1.3715.3.5
		bkd OBJECT IDENTIFIER ::= { bk 5 }

		
		-- 1.3.6.1.4.1.3715.3.5.200
		bkd200 OBJECT IDENTIFIER ::= { bkd 200 }

		
-- 
-- 
		-- 1.3.6.1.4.1.3715.3.5.200.1
		generation OBJECT-TYPE
			SYNTAX INTEGER
			ACCESS read-only
			STATUS mandatory
			DESCRIPTION
				"BKD200 generation.
				1 = 1st generation."
			::= { bkd200 1 }

		
		-- 1.3.6.1.4.1.3715.3.5.200.2
		psu5V8 OBJECT-TYPE
			SYNTAX INTEGER
			ACCESS read-only
			STATUS mandatory
			DESCRIPTION
				"+5.8 VDC voltage from power supply. Unit 0.01 V.
				This object has an entry in the propertyTable."
			::= { bkd200 2 }

		
		-- 1.3.6.1.4.1.3715.3.5.200.3
		usTestpointSelection OBJECT-TYPE
			SYNTAX INTEGER
				{
				usTestpointSelectionAutomatic(1),
				usTestpointSelectionManualUS0(2),
				usTestpointSelectionManualUS1(3)
				}
			ACCESS read-write
			STATUS mandatory
			DESCRIPTION
				"US test point selection: 
				1: automatic, 
				2: manual US0, 
				3: manual US1
				"
			::= { bkd200 3 }

		
	
	END

--
-- TELESTE-BK-MIB.mib
--
