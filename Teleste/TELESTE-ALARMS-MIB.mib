--
-- TELESTE-ALARMS-MIB.mib
-- MIB generated by MG-SOFT Visual MIB Builder Version 4.0 Build 349
-- Thursday, January 03, 2008 at 12:58:49
--

-- *****************************************************************************
-- Copyright (c) 2002-2008 by:
-- 
-- Teleste Corporation
-- Seponkatu 1
-- FIN-20660 Littoinen, Finland
-- tel. +358 2 2605 611
-- url: http://www.teleste.com
-- 
-- Description: Common event log for all Teleste products
-- 
-- Revision History:
-- -----------------
-- 1.1 30.11.2007 Matti Susi
-- - added severity level Notify(8)
-- 
-- 1.0  1.9.2004 Matti Susi
-- - First official release
-- 
-- ****************************************************************************
-- 

	TELESTE-ALARMS-MIB DEFINITIONS ::= BEGIN
 
		IMPORTS
			OBJECT-TYPE			
				FROM RFC-1212			
			TRAP-TYPE			
				FROM RFC-1215			
			DisplayString			
				FROM RFC1213-MIB			
			elementName			
				FROM TELESTE-COMMON-MIB			
			functional, teleste			
				FROM TELESTE-ROOT-MIB;
	
	
	
--
-- Node definitions
--
	
-- Teleste standard alarm objects
		-- 1.3.6.1.4.1.3715.100.100
		alarms OBJECT IDENTIFIER ::= { functional 100 }

		
		-- 1.3.6.1.4.1.3715.100.100.1
		eventLogNumberOfEntries OBJECT-TYPE
			SYNTAX INTEGER
			ACCESS read-only
			STATUS mandatory
			DESCRIPTION
				"Current number of entries in the eventLogTable."
			::= { alarms 1 }

		
		-- 1.3.6.1.4.1.3715.100.100.2
		eventLogLastIndex OBJECT-TYPE
			SYNTAX INTEGER
			ACCESS read-only
			STATUS mandatory
			DESCRIPTION
				"Index of the most recent event entry logged in the
				eventLogTable."
			::= { alarms 2 }

		
		-- 1.3.6.1.4.1.3715.100.100.3
		eventTrapEnable OBJECT-TYPE
			SYNTAX INTEGER
				{
				trapDisable(1),
				trapEnableBoth(2),
				trapEnableTeleste(3),
				trapEnableHMS(4)
				}
			ACCESS read-write
			STATUS mandatory
			DESCRIPTION
				"This object controls sending and format of alarm traps:
				1 = disable sending of all traps
				2 = enable both Teleste and HMS Traps
				3 = enable Teleste alarmEvent traps (HMS traps disabled)
				4 = enable HMS alarmEvent traps (Teleste traps disabled)
				This object has no effect on MIB-2 traps."
			::= { alarms 3 }

		
		-- 1.3.6.1.4.1.3715.100.100.4
		eventLogTable OBJECT-TYPE
			SYNTAX SEQUENCE OF EventLogEntry
			ACCESS not-accessible
			STATUS mandatory
			DESCRIPTION
				"A list of events that have been logged. The agent generates
				an alarmEvent trap every time a new event entry is logged.
				This table should support a minimum of 10 entries."
			::= { alarms 4 }

		
		-- 1.3.6.1.4.1.3715.100.100.4.1
		eventLogEntry OBJECT-TYPE
			SYNTAX EventLogEntry
			ACCESS not-accessible
			STATUS mandatory
			DESCRIPTION
				"A row in the table."
			INDEX { eventIndex }
			::= { eventLogTable 1 }

		
		EventLogEntry ::=
			SEQUENCE { 
				eventIndex
					INTEGER,
				eventTime
					DisplayString,
				eventSeverity
					INTEGER,
				eventParameterOID
					OBJECT IDENTIFIER,
				eventParameterValue
					INTEGER
			 }

		-- 1.3.6.1.4.1.3715.100.100.4.1.1
		eventIndex OBJECT-TYPE
			SYNTAX INTEGER (1..32767)
			ACCESS read-only
			STATUS mandatory
			DESCRIPTION
				"An index that uniquely identifies an entry in the event 
				log table. When the log becomes full, the agent will start
				to remove oldest events from the log."
			::= { eventLogEntry 1 }

		
		-- 1.3.6.1.4.1.3715.100.100.4.1.2
		eventTime OBJECT-TYPE
			SYNTAX DisplayString
			ACCESS read-only
			STATUS mandatory
			DESCRIPTION
				"The date and time of the alarm event. Displayed in 
				human-readable format."
			::= { eventLogEntry 2 }

		
		-- 1.3.6.1.4.1.3715.100.100.4.1.3
		eventSeverity OBJECT-TYPE
			SYNTAX INTEGER
				{
				sevNominal(1),
				sevHiHi(2),
				sevHi(3),
				sevLo(4),
				sevLoLo(5),
				sevMajor(6),
				sevMinor(7),
				sevNotify(8)
				}
			ACCESS read-only
			STATUS mandatory
			DESCRIPTION
				"Event severity (type):
				sevNominal(1) = Nominal
				sevHiHi(2) = HIHI
				sevHi(3) = HI
				sevLo(4) = LO
				sevLoLo(5) = LOLO
				sevMajor(6) = Discrete Major
				sevMinor(7) = Discrete Minor
				devNotify(8) = Discrete Notify "
			::= { eventLogEntry 3 }

		
		-- 1.3.6.1.4.1.3715.100.100.4.1.4
		eventParameterOID OBJECT-TYPE
			SYNTAX OBJECT IDENTIFIER
			ACCESS read-only
			STATUS mandatory
			DESCRIPTION
				"OID of the parameter that originated the alarm event."
			::= { eventLogEntry 4 }

		
		-- 1.3.6.1.4.1.3715.100.100.4.1.5
		eventParameterValue OBJECT-TYPE
			SYNTAX INTEGER
			ACCESS read-only
			STATUS mandatory
			DESCRIPTION
				"Value of the parameter when the alarm event occurred."
			::= { eventLogEntry 5 }

		
		-- 1.3.6.1.4.1.3715.100.100.5
		eventText OBJECT-TYPE
			SYNTAX DisplayString
			ACCESS not-accessible
			STATUS optional
			DESCRIPTION
				"A verbal explanation of the event in the format:
				Severity: Parameter (value).
				This object is only an OID reference for the variable 
				binding in the alarmEvent trap and is not-accessible 
				as such."
			::= { alarms 5 }

		
	
--
-- Trap definitions
--
	
-- Trap definitions
		alarmEvent TRAP-TYPE 
			ENTERPRISE teleste
			VARIABLES { elementName, eventTime, eventSeverity, eventParameterOID, eventParameterValue, 
				eventText }
			DESCRIPTION 
				"The trap generated when an new alarm event happens."
			::=  1

	
	END

--
-- TELESTE-ALARMS-MIB.mib
--
