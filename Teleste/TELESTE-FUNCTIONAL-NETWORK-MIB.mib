--
-- TELESTE-FUNCTIONAL-NETWORK-MIB.mib
-- MIB generated by MG-SOFT Visual MIB Builder 2021 (64-bit) Version 15.00  Build 1510
-- Friday, September 17, 2021 at 13:10:11
--

-- Teleste functional network MIB.
-- 
-- Version history (latest change at the top)
-- 
-- 7, 17.9.2021, Sami Kuusisto
-- - Added switch PHY settings in networkPhy group.
-- 
-- 6, 16.2.2021, Sami Kuusisto
-- - Improved networkIPv4InterfaceGlobalServicesEnable and networkIPv6InterfaceGlobalServicesEnable description.
-- 
-- 5, 12.2.2021, Sami Kuusisto
-- - Some fine tuning.
-- 
-- 4, 9.2.2021, Sami Kuusisto
-- - Refactored.
-- 
-- 3, 3.2.2021, Sami Kuusisto
-- - Improved descriptions.
-- 
-- 2, 2.2.2021, Sami Kuusisto
-- - Refactored.
-- 
-- 1, 1.2.2021, Sami Kuusisto
-- - Initial version.
-- 
-- 

	TELESTE-FUNCTIONAL-NETWORK-MIB DEFINITIONS ::= BEGIN
 
		IMPORTS
			OBJECT-GROUP			
				FROM SNMPv2-CONF			
			Integer32, Counter64, BITS, OBJECT-TYPE, MODULE-IDENTITY			
				FROM SNMPv2-SMI			
			functional			
				FROM TELESTE-ROOT-MIB;
	
	
		-- 1.3.6.1.4.1.3715.100.104
		network MODULE-IDENTITY 
			LAST-UPDATED "202109171200Z"		-- September 17, 2021 at 12:00 GMT
			ORGANIZATION 
				"Teleste Oyj"
			CONTACT-INFO 
				"support@teleste.com"
			DESCRIPTION 
				"Teleste functional MIB for network related settings."
			::= { functional 104 }

		
	
--
-- Type definitions
--
	
-- Bit positions used to indicate service
-- 0:  TSEMP
-- 1:  Reserved for future purposes
-- 2:  Reserved for future purposes
-- 3:  Reserved for future purposes
-- 
-- 4:  SNMPv1; used when device supports SNMP enable/disable per SNMP version. 
-- 5:  SNMPv2c; used when device supports SNMP enable/disable per SNMP version.
-- 6:  SNMPv3; used when device supports SNMP enable/disable per SNMP version.
-- 7:  SNMPv1/v2c/v3; used when device supports only SNMP service enable/disable in general, not per SNMP version
-- 
-- 8:  HTTP
-- 9:  HTTPS
-- 10: Rserved for future purposes
-- 11: Reserved for future purposes
-- 
-- 12: telnet
-- 13: ssh
-- 14: Reserved for future purposes
-- 15: Reserved for future purposes
-- 
-- 16: tftp
-- 17: ftp
-- 18: sftp
-- 19: scp
-- 
-- 20: Reserved for future purposes
-- ..
-- 31: Reserved for future purposes
-- 
		NetworkInterfaceServices ::= BITS
			{
			nisTSEMP(0),
			nisReserved1(1),
			nisReserved2(2),
			nisReserved3(3),
			nisSNMPv1(4),
			nisSNMPv2c(5),
			nisSNMPv3(6),
			nisSNMP(7),
			nisHTTP(8),
			nisHTTPS(9),
			nisReserved10(10),
			nisReserved11(11),
			nisTelnet(12),
			nisSsh(13),
			nisReserved14(14),
			nisReserved15(15),
			nisTFTP(16),
			nisFTP(17),
			nisSFTP(18),
			nisSCP(19),
			nisReserved20(20),
			nisReserved21(21),
			nisReserved22(22),
			nisReserved23(23),
			nisReserved24(24),
			nisReserved25(25),
			nisReserved26(26),
			nisReserved27(27),
			nisReserved28(28),
			nisReserved29(29),
			nisReserved30(30),
			nisReserved31(31)
			}

-- Network interface type
-- 
-- 0x00	Not available
-- 0x01	Unknown
-- 0x06	Ethernet
-- 0x16	RPD Ethernet
-- 0x31	Atm Adaptation Layer 5
-- 0xe9	IP via Serial Port
-- 0xea	Legacy USB
-- (legacy TSEMP/DVX)
-- 0xeb	Routed USB
-- (both legacy TSEMP/DVX and new x/RSIP/DVX (e.g. TSEMP/RSIP/DVX and SNMP/RSIP/DVX)
-- 0xf6	RPD remote management
-- 0xf7	RPD local management
-- 0xf8	BK (Proxy)
-- 0xf9	DVX (Proxy)
-- 0xfa	RPD UART (private/internal use)
-- 0xfb	HFC RIS MAC
-- 0xfc	HFC DOCSIS MAC
-- 0xfd	HFC HMS MAC
-- 0xfe	HFC Teleste MAC
-- 
		NetworkInterfaceType ::= INTEGER
			{
			networkInterfaceTypeUnkown(1),
			networkInterfaceTypeEthernet(6),
			networkInterfaceTypeRpdEthernet(22),
			networkInterfaceTypeAtmAdaptatioLayer5(49),
			networkInterfaceTypeIpViaSerialPort(233),
			networkInterfaceTypeLegacyUsb(234),
			networkInterfaceTypeRoutedUsb(235),
			networkInterfaceTypeRpdRemoteManagement(246),
			networknterfaceTypeRpdLocalManagement(247),
			networkInterfaceTypeBkProxy(248),
			networkInterfaceTypeDvxProxy(249),
			networkInterfaceTypeRpdUart(250),
			networkInterfaceTypeHfcRisMac(251),
			networkInterfaceTypeHfcDocsisMac(252),
			networkInterfaceTypeHfcHmsMac(253),
			networkInterfaceTypeCatvisorMac(254),
			networkInterfaceTypeNA(255)
			}

-- Network interface/port (software wise) enable/disable control.
-- 
-- 1: Port is enabled/allowed to communicate (software wise). Port may be powered down or up depending cable connections.
-- 2: Port is disabled/disallowed to communicate (software wise).
		NetworkInterfacePortEnable ::= INTEGER
			{
			networkInterfaceEnabled(1),
			networkInterfaceDisabled(2)
			}

	
--
-- Node definitions
--
	
		-- 1.3.6.1.4.1.3715.100.104.1
		networkIPv4 OBJECT IDENTIFIER ::= { network 1 }
-- IPv4 related stuff.
		
		-- 1.3.6.1.4.1.3715.100.104.1.1
		networkNumberOfIPv4Interfaces OBJECT-TYPE
			SYNTAX Integer32
			MAX-ACCESS read-only
			STATUS current
			DESCRIPTION
				"Number of IPv4 network like interfaces.
				
				If there's no active IPv4 interfaces, then 1 interface should be reported with type N/A (networkInterfaceTypeNA(255))."
			::= { networkIPv4 1 }

		
		-- 1.3.6.1.4.1.3715.100.104.1.2
		networkIPv4InterfaceGlobalServicesEnable OBJECT-TYPE
			SYNTAX NetworkInterfaceServices
			MAX-ACCESS read-only
			STATUS current
			DESCRIPTION
				"IPv4 services control method per service.
				
				Global services (per device)
				If service bit is set (at networkIPv4InterfaceGlobalServicesEnable), service supports only global (per device) control and does not support per interface/per port control.
				Global service state should be get and set (enabled/disabled) by using port that supports this service (indicated in networkIPv4InterfaceServices). So when changing global
				service state using one port, result is seen in all other ports. Device may support global service control by using any port.
				
				Per port services
				If service bit is cleared (networkIPv4InterfaceGlobalServicesEnable), service supports per interface/per port control.
				Per port service state is get and set (enabled/disabled) by using spesific port networkIPv4InterfaceServices.
				
				NOTE! Changing IPv4 services may affect IPv6 services too. This is device dependant."
			::= { networkIPv4 2 }

		
		-- 1.3.6.1.4.1.3715.100.104.1.3
		networkIPv4InterfaceTable OBJECT-TYPE
			SYNTAX SEQUENCE OF NetworkIPv4InterfaceEntry
			MAX-ACCESS not-accessible
			STATUS current
			DESCRIPTION
				"IPv4 network interface table."
			::= { networkIPv4 3 }

		
		-- 1.3.6.1.4.1.3715.100.104.1.3.1
		networkIPv4InterfaceEntry OBJECT-TYPE
			SYNTAX NetworkIPv4InterfaceEntry
			MAX-ACCESS not-accessible
			STATUS current
			DESCRIPTION
				"IPv4 network interface table."
			INDEX { networkIPv4InterfaceTableIndex }
			::= { networkIPv4InterfaceTable 1 }

		
		NetworkIPv4InterfaceEntry ::=
			SEQUENCE { 
				networkIPv4InterfaceTableIndex
					Integer32,
				networkIPv4InterfaceType
					NetworkInterfaceType,
				networkIPv4InterfaceEnable
					NetworkInterfacePortEnable,
				networkIPv4InterfaceServices
					NetworkInterfaceServices,
				networkIPv4InterfaceSupportedServices
					NetworkInterfaceServices,
				networkIPv4InterfaceUdpRxPort
					Integer32
			 }

		-- 1.3.6.1.4.1.3715.100.104.1.3.1.1
		networkIPv4InterfaceTableIndex OBJECT-TYPE
			SYNTAX Integer32 (1..128)
			MAX-ACCESS read-only
			STATUS current
			DESCRIPTION
				"Index to networkIPv4Table.
				
				If there's no active IPv4 interfaces, then 1 interface should be reported with type N/A (networkInterfaceTypeNA(255))."
			::= { networkIPv4InterfaceEntry 1 }

		
		-- 1.3.6.1.4.1.3715.100.104.1.3.1.2
		networkIPv4InterfaceType OBJECT-TYPE
			SYNTAX NetworkInterfaceType
			MAX-ACCESS read-only
			STATUS current
			DESCRIPTION
				"IPv4 network interface type.
				
				See NetworkInterfaceType type assignment for descriptions."
			::= { networkIPv4InterfaceEntry 2 }

		
		-- 1.3.6.1.4.1.3715.100.104.1.3.1.3
		networkIPv4InterfaceEnable OBJECT-TYPE
			SYNTAX NetworkInterfacePortEnable
			MAX-ACCESS read-write
			STATUS current
			DESCRIPTION
				"Get and set state of the IPv4 port. Port state can be either enabled (1) or disabled (2).
				
				Command is not interface type specific (Ethernet, IPv4, IPv6, HFC, DOCSIS, USB, DVX etc.). So enabling/disabling IPv4 port may affect IPv6 port too (or may not).
				
				See NetworkInterfacePortEnable type assignment for descriptions.
				
				"
			::= { networkIPv4InterfaceEntry 3 }

		
		-- 1.3.6.1.4.1.3715.100.104.1.3.1.4
		networkIPv4InterfaceServices OBJECT-TYPE
			SYNTAX NetworkInterfaceServices
			MAX-ACCESS read-write
			STATUS current
			DESCRIPTION
				"Get and set service status of IPv4 port.
				
				Supported services: see networkIPv4InterfaceSupportedServices.
				
				Device may support service control per port or just global service enable/disable per device: see networkIPv4InterfaceGlobalServicesEnable.
				
				Services are enabled by networkIPv4InterfaceServices. Enabled service has corresponding service bit set.
				Services are disabled by networkIPv4InterfaceServices. Disabled service has corresponding service bit cleared.
				
				Enabling already enabled service, does not affect service.
				Disabling already disabled service, does not affect service.
				
				NOTE! Enabling or disabling IPv4 services may (or may not) affect IPv6 services. This is device dependant.
				
				NOTE! It is not recommended to disable all services, but to prevent user making device inaccessible, 
				device keeps one service at one port enabled, if all services at all ports of device is going to be 
				disabled. The service and port is device dependent.
				
				See NetworkInterfaceServices type assignment for descriptions."
			::= { networkIPv4InterfaceEntry 4 }

		
		-- 1.3.6.1.4.1.3715.100.104.1.3.1.5
		networkIPv4InterfaceSupportedServices OBJECT-TYPE
			SYNTAX NetworkInterfaceServices
			MAX-ACCESS read-only
			STATUS current
			DESCRIPTION
				"IPv4 services supported by device. 
				
				If service is supported, service related bit is set. 
				If service is not supported, service related bit is cleared.
				
				See NetworkInterfaceServices type assignment for descriptions."
			::= { networkIPv4InterfaceEntry 5 }

		
		-- 1.3.6.1.4.1.3715.100.104.1.3.1.6
		networkIPv4InterfaceUdpRxPort OBJECT-TYPE
			SYNTAX Integer32 (0..65535)
			MAX-ACCESS read-write
			STATUS current
			DESCRIPTION
				"This OID can be used to get and set one IPv4 service's UDP receiving port. Service is device and interface/port dependant.
				This OID may be read-only or read-write. This is device and interface/port dependant.
				
				0: This OID is not in use. 
				1-65535: UDP port used to listen packets."
			::= { networkIPv4InterfaceEntry 6 }

		
		-- 1.3.6.1.4.1.3715.100.104.2
		networkIPv6 OBJECT IDENTIFIER ::= { network 2 }
-- IPv6 related stuff.
		
		-- 1.3.6.1.4.1.3715.100.104.2.1
		networkNumberOfIPv6Interfaces OBJECT-TYPE
			SYNTAX Integer32
			MAX-ACCESS read-only
			STATUS current
			DESCRIPTION
				"Number of IPv6 network like interfaces.
				
				If there's no active IPv6 interfaces, then 1 interface should be reported with type N/A (networkInterfaceTypeNA(255))."
			::= { networkIPv6 1 }

		
		-- 1.3.6.1.4.1.3715.100.104.2.2
		networkIPv6InterfaceGlobalServicesEnable OBJECT-TYPE
			SYNTAX NetworkInterfaceServices
			MAX-ACCESS read-only
			STATUS current
			DESCRIPTION
				"IPv6 services control method per service.
				
				Global services (per device)
				If service bit is set (at networkIPv6InterfaceGlobalServicesEnable), service supports only global (per device) control and does not support per interface/per port control.
				Global service state should be get and set (enabled/disabled) by using port that supports this service (indicated in networkIPv6InterfaceServices). So when changing global 
				service state using one port, result is seen in all other ports. Device may support global service control by using any port.
				
				Per port services
				If service bit is cleared (networkIPv6InterfaceGlobalServicesEnable), service supports per interface/per port control.
				Per port service state is get and set (enabled/disabled) by using spesific port networkIPv6InterfaceServices.
				
				NOTE! Changing IPv6 services may affect IPv4 services too. This is device dependant."
			::= { networkIPv6 2 }

		
		-- 1.3.6.1.4.1.3715.100.104.2.3
		networkIPv6InterfaceTable OBJECT-TYPE
			SYNTAX SEQUENCE OF NetworkIPv6InterfaceEntry
			MAX-ACCESS not-accessible
			STATUS current
			DESCRIPTION
				"IPv6 network interface table."
			::= { networkIPv6 3 }

		
		-- 1.3.6.1.4.1.3715.100.104.2.3.1
		networkIPv6InterfaceEntry OBJECT-TYPE
			SYNTAX NetworkIPv6InterfaceEntry
			MAX-ACCESS not-accessible
			STATUS current
			DESCRIPTION
				"IPv6 network interface table."
			INDEX { networkIPv6InterfaceTableIndex }
			::= { networkIPv6InterfaceTable 1 }

		
		NetworkIPv6InterfaceEntry ::=
			SEQUENCE { 
				networkIPv6InterfaceTableIndex
					Integer32,
				networkIPv6InterfaceType
					NetworkInterfaceType,
				networkIPv6InterfaceEnable
					NetworkInterfacePortEnable,
				networkIPv6InterfaceServices
					NetworkInterfaceServices,
				networkIPv6InterfaceSupportedServices
					NetworkInterfaceServices,
				networkIPv6InterfaceUdpRxPort
					Integer32
			 }

		-- 1.3.6.1.4.1.3715.100.104.2.3.1.1
		networkIPv6InterfaceTableIndex OBJECT-TYPE
			SYNTAX Integer32 (1..128)
			MAX-ACCESS read-only
			STATUS current
			DESCRIPTION
				"Index to networkIPv6Table.
				
				If there's no active IPv6 interfaces, then 1 interface should be reported with type N/A (networkInterfaceTypeNA(255))."
			::= { networkIPv6InterfaceEntry 1 }

		
		-- 1.3.6.1.4.1.3715.100.104.2.3.1.2
		networkIPv6InterfaceType OBJECT-TYPE
			SYNTAX NetworkInterfaceType
			MAX-ACCESS read-only
			STATUS current
			DESCRIPTION
				"IPv6 network interface type.
				
				See NetworkInterfaceType type assignment for descriptions."
			::= { networkIPv6InterfaceEntry 2 }

		
		-- 1.3.6.1.4.1.3715.100.104.2.3.1.3
		networkIPv6InterfaceEnable OBJECT-TYPE
			SYNTAX NetworkInterfacePortEnable
			MAX-ACCESS read-write
			STATUS current
			DESCRIPTION
				"Get and set state of the IPv6 port. Port state can be either enabled (1) or disabled (2).
				
				Command is not interface type specific (Ethernet, IPv4, IPv6, HFC, DOCSIS, USB, DVX etc.). So enabling/disabling IPv6 port may affect IPv4 port too (or may not).
				
				See NetworkInterfacePortEnable type assignment for descriptions."
			::= { networkIPv6InterfaceEntry 3 }

		
		-- 1.3.6.1.4.1.3715.100.104.2.3.1.4
		networkIPv6InterfaceServices OBJECT-TYPE
			SYNTAX NetworkInterfaceServices
			MAX-ACCESS read-write
			STATUS current
			DESCRIPTION
				"Get and set service status of IPv6 port.
				
				Supported services: see networkIPv6InterfaceSupportedServices.
				
				Device may support service control per port or just global service enable/disable per device: see networkIPv6InterfaceGlobalServicesEnable.
				
				Services are enabled by networkIPv6InterfaceServices. Enabled service has corresponding service bit set.
				Services are disabled by networkIPv6InterfaceServices. Disabled service has corresponding service bit cleared.
				
				Enabling already enabled service, does not affect service.
				Disabling already disabled service, does not affect service.
				
				NOTE! Enabling or disabling IPv6 services may (or may not) affect IPv4 services. This is device dependant.
				
				NOTE! It is not recommended to disable all services, but to prevent user making device inaccessible, 
				device keeps one service at one port enabled, if all services at all ports of device is going to be 
				disabled. The service and port is device dependent.
				
				See NetworkInterfaceServices type assignment for descriptions."
			::= { networkIPv6InterfaceEntry 4 }

		
		-- 1.3.6.1.4.1.3715.100.104.2.3.1.5
		networkIPv6InterfaceSupportedServices OBJECT-TYPE
			SYNTAX NetworkInterfaceServices
			MAX-ACCESS read-only
			STATUS current
			DESCRIPTION
				"IPv6 services supported by device.
				
				If service is supported, service related bit is set. 
				If service is not supported, service related bit is cleared.
				
				See NetworkInterfaceServices type assignment for descriptions."
			::= { networkIPv6InterfaceEntry 5 }

		
		-- 1.3.6.1.4.1.3715.100.104.2.3.1.6
		networkIPv6InterfaceUdpRxPort OBJECT-TYPE
			SYNTAX Integer32 (0..65535)
			MAX-ACCESS read-write
			STATUS current
			DESCRIPTION
				"This OID can be used to get and set one IPv6 service's UDP receiving port. Service is device and interface/port dependant.
				This OID may be read-only or read-write. This is device and interface/port dependant.
				
				0: This OID is not in use. 
				1-65535: UDP port used to listen packets."
			::= { networkIPv6InterfaceEntry 6 }

		
		-- 1.3.6.1.4.1.3715.100.104.3
		networkPhy OBJECT IDENTIFIER ::= { network 3 }
-- PHY related stuff.
		
		-- 1.3.6.1.4.1.3715.100.104.3.1
		networkNumberOfPhyPorts OBJECT-TYPE
			SYNTAX Integer32
			MAX-ACCESS read-only
			STATUS current
			DESCRIPTION
				"Number of PHY ports.
				
				If there's no PHY ports, then 0 should be reported."
			::= { networkPhy 1 }

		
		-- 1.3.6.1.4.1.3715.100.104.3.2
		networkPhyPortsTable OBJECT-TYPE
			SYNTAX SEQUENCE OF NetworkPhyPortsEntry
			MAX-ACCESS not-accessible
			STATUS current
			DESCRIPTION
				"PHY ports table."
			::= { networkPhy 2 }

		
		-- 1.3.6.1.4.1.3715.100.104.3.2.1
		networkPhyPortsEntry OBJECT-TYPE
			SYNTAX NetworkPhyPortsEntry
			MAX-ACCESS not-accessible
			STATUS current
			DESCRIPTION
				"PHY ports table."
			INDEX { networkPhyPortsTableIndex }
			::= { networkPhyPortsTable 1 }

		
		NetworkPhyPortsEntry ::=
			SEQUENCE { 
				networkPhyPortsTableIndex
					Integer32,
				networkPhyPortsDescription
					OCTET STRING,
				networkPhyPortsInterfaceDescription
					OCTET STRING,
				networkPhyPortsControl
					INTEGER,
				networkPhyPortsLinkStatus
					INTEGER,
				networkPhyPortsDuplex
					INTEGER,
				networkPhyPortsSpeed
					Counter64
			 }

		-- 1.3.6.1.4.1.3715.100.104.3.2.1.1
		networkPhyPortsTableIndex OBJECT-TYPE
			SYNTAX Integer32 (1..128)
			MAX-ACCESS read-write
			STATUS current
			DESCRIPTION
				"Index to networkPhyPortsTable
				
				If there's no PHYs, then this table is empty. See networkNumberOfPhyPorts which reports 0 in such case."
			::= { networkPhyPortsEntry 1 }

		
		-- 1.3.6.1.4.1.3715.100.104.3.2.1.2
		networkPhyPortsDescription OBJECT-TYPE
			SYNTAX OCTET STRING
			MAX-ACCESS read-only
			STATUS current
			DESCRIPTION
				"PHY port textual description (to help identifying physical port)."
			::= { networkPhyPortsEntry 2 }

		
		-- 1.3.6.1.4.1.3715.100.104.3.2.1.3
		networkPhyPortsInterfaceDescription OBJECT-TYPE
			SYNTAX OCTET STRING
			MAX-ACCESS read-only
			STATUS current
			DESCRIPTION
				"Network interface textual description (to help identifying physical port) which is connected to this PHY port."
			::= { networkPhyPortsEntry 3 }

		
		-- 1.3.6.1.4.1.3715.100.104.3.2.1.4
		networkPhyPortsControl OBJECT-TYPE
			SYNTAX INTEGER
				{
				networkPhyPortControlEnabled(1),
				networkPhyPortControlDisabled(2)
				}
			MAX-ACCESS read-write
			STATUS current
			DESCRIPTION
				"PHY port enable/disable control.
				
				1: PHY port enabled.
				2: PHY port disabled."
			::= { networkPhyPortsEntry 4 }

		
		-- 1.3.6.1.4.1.3715.100.104.3.2.1.5
		networkPhyPortsLinkStatus OBJECT-TYPE
			SYNTAX INTEGER
				{
				networkPhyPortLinkStatusLinkUp(1),
				networkPhyPortLinkStatusLinkDown(2)
				}
			MAX-ACCESS read-only
			STATUS current
			DESCRIPTION
				"PHY port link status.
				
				1: Link up.
				2: Link down."
			::= { networkPhyPortsEntry 5 }

		
		-- 1.3.6.1.4.1.3715.100.104.3.2.1.6
		networkPhyPortsDuplex OBJECT-TYPE
			SYNTAX INTEGER
				{
				networkPhyPortDuplexFull(1),
				networkPhyPortDuplexHalf(2)
				}
			MAX-ACCESS read-write
			STATUS current
			DESCRIPTION
				"PHY port duplex.
				
				1: Full duplex.
				2: Half duplex."
			::= { networkPhyPortsEntry 6 }

		
		-- 1.3.6.1.4.1.3715.100.104.3.2.1.7
		networkPhyPortsSpeed OBJECT-TYPE
			SYNTAX Counter64
			MAX-ACCESS read-only
			STATUS current
			DESCRIPTION
				"Nominal link speed used by PHY.
				
				Unit 1 bps."
			::= { networkPhyPortsEntry 7 }

		
		-- 1.3.6.1.4.1.3715.100.104.99
		networkConformance OBJECT IDENTIFIER ::= { network 99 }

		
		-- 1.3.6.1.4.1.3715.100.104.99.1
		networkGroups OBJECT IDENTIFIER ::= { networkConformance 1 }

		
		-- 1.3.6.1.4.1.3715.100.104.99.1.1
		networkIPv4ObjectGroup OBJECT-GROUP
			OBJECTS { networkNumberOfIPv4Interfaces, networkIPv4InterfaceGlobalServicesEnable, networkIPv4InterfaceTableIndex, networkIPv4InterfaceType, networkIPv4InterfaceEnable, 
				networkIPv4InterfaceServices, networkIPv4InterfaceSupportedServices, networkIPv4InterfaceUdpRxPort }
			STATUS current
			DESCRIPTION 
				"Description."
			::= { networkGroups 1 }

		
		-- 1.3.6.1.4.1.3715.100.104.99.1.2
		networkIPv6ObjectGroup OBJECT-GROUP
			OBJECTS { networkNumberOfIPv6Interfaces, networkIPv6InterfaceGlobalServicesEnable, networkIPv6InterfaceTableIndex, networkIPv6InterfaceType, networkIPv6InterfaceEnable, 
				networkIPv6InterfaceServices, networkIPv6InterfaceSupportedServices, networkIPv6InterfaceUdpRxPort }
			STATUS current
			DESCRIPTION 
				"Description."
			::= { networkGroups 2 }

		
		-- 1.3.6.1.4.1.3715.100.104.99.1.3
		networkPhyObjectGroup OBJECT-GROUP
			OBJECTS { networkNumberOfPhyPorts, networkPhyPortsTableIndex, networkPhyPortsDescription, networkPhyPortsInterfaceDescription, networkPhyPortsControl, 
				networkPhyPortsLinkStatus, networkPhyPortsDuplex, networkPhyPortsSpeed }
			STATUS current
			DESCRIPTION 
				"Description."
			::= { networkGroups 3 }

		
	
	END

--
-- TELESTE-FUNCTIONAL-NETWORK-MIB.mib
--
