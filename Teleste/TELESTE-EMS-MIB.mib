--
-- TELESTE-EMS-MIB.mib
-- MIB generated by MG-SOFT Visual MIB Builder Version 4.0 Build 349
-- Tuesday, February 28, 2006 at 13:15:45
--

-- *****************************************************************************
-- Copyright (c) 2000-2003 by:
-- 
-- Teleste Corporation
-- Seponkatu 1
-- FIN-20660 Littoinen, Finland
-- tel. +358 2 2605 611
-- url: http://www.teleste.com
-- 
-- Description: CATVisor EMS Server MIB (SNMP Wizard)
-- 
-- Revision History:
-- -----------------
-- 1.2, 28.2.2006 Matti Susi
-- - replaced defined object identifier 'emsServer' with 'ems'
--   imported from TELESTE-ROOT-MIB
-- 
-- 1.1, 3.12.2003 Matti Susi
-- - added object eventLogMessageID
-- 
-- 1.0, 12.12.2002 Matti Susi
-- - New name for TELESTE-WIZ-MIB
-- 
-- *****************************************************************************

	TELESTE-EMS-MIB DEFINITIONS ::= BEGIN
 
		IMPORTS
			OBJECT-TYPE			
				FROM RFC-1212			
			TRAP-TYPE			
				FROM RFC-1215			
			NetworkAddress			
				FROM RFC1155-SMI			
			DisplayString			
				FROM RFC1213-MIB			
			ems, DateAndTime			
				FROM TELESTE-ROOT-MIB;
	
	
	
--
-- Node definitions
--
	
		-- 1.3.6.1.4.1.3715.1.1
		emsServerProperties OBJECT IDENTIFIER ::= { ems 1 }

		
		-- 1.3.6.1.4.1.3715.1.1.1
		serverName OBJECT-TYPE
			SYNTAX DisplayString
			ACCESS read-only
			STATUS mandatory
			DESCRIPTION
				"The name of the EMS Server."
			::= { emsServerProperties 1 }

		
		-- 1.3.6.1.4.1.3715.1.1.2
		serverTimeSinceLastResponse OBJECT-TYPE
			SYNTAX INTEGER
			ACCESS read-only
			STATUS mandatory
			DESCRIPTION
				"Time since the last response from the EMS Server.
				Unit 1 second."
			::= { emsServerProperties 2 }

		
		-- 1.3.6.1.4.1.3715.1.1.3
		serverNoResponseTimeOut OBJECT-TYPE
			SYNTAX INTEGER
			ACCESS read-write
			STATUS mandatory
			DESCRIPTION
				"Number of seconds until the noResponse-trap is sent
				when the agent has lost connection to the EMS Server.
				"
			::= { emsServerProperties 3 }

		
		-- 1.3.6.1.4.1.3715.1.2
		emsServerEvents OBJECT IDENTIFIER ::= { ems 2 }

		
		-- 1.3.6.1.4.1.3715.1.2.1
		emsEventLogInfo OBJECT IDENTIFIER ::= { emsServerEvents 1 }

		
		-- 1.3.6.1.4.1.3715.1.2.1.1
		eventLogActiveAlarms OBJECT-TYPE
			SYNTAX INTEGER
			ACCESS read-only
			STATUS mandatory
			DESCRIPTION
				"The number of active alarms on the EMS Server's
				event log."
			::= { emsEventLogInfo 1 }

		
		-- 1.3.6.1.4.1.3715.1.2.1.2
		eventLogActiveWarnings OBJECT-TYPE
			SYNTAX INTEGER
			ACCESS read-only
			STATUS mandatory
			DESCRIPTION
				"The number of active warnings on the EMS Server's
				event log."
			::= { emsEventLogInfo 2 }

		
		-- 1.3.6.1.4.1.3715.1.2.1.3
		eventLogActiveNotifications OBJECT-TYPE
			SYNTAX INTEGER
			ACCESS read-only
			STATUS mandatory
			DESCRIPTION
				"The number of active notifications on the EMS Server's
				event log."
			::= { emsEventLogInfo 3 }

		
		-- 1.3.6.1.4.1.3715.1.2.1.4
		eventLogNumberOfEntries OBJECT-TYPE
			SYNTAX INTEGER
			ACCESS read-only
			STATUS mandatory
			DESCRIPTION
				"The number of entries in the emsEventLogTable."
			::= { emsEventLogInfo 4 }

		
		-- 1.3.6.1.4.1.3715.1.2.1.5
		eventLogLastIndex OBJECT-TYPE
			SYNTAX INTEGER
			ACCESS read-only
			STATUS mandatory
			DESCRIPTION
				"The last index in the emsEventLogTable. The last index 
				value can be used as an indicator for table changes."
			::= { emsEventLogInfo 5 }

		
		-- 1.3.6.1.4.1.3715.1.2.1.6
		eventLogMessageID OBJECT-TYPE
			SYNTAX INTEGER
			ACCESS not-accessible
			STATUS mandatory
			DESCRIPTION
				"A unique number for identifying the event message. This
				object is just an OID placeholder and gets a value only 
				at the time a trap is being sent."
			::= { emsEventLogInfo 6 }

		
		-- 1.3.6.1.4.1.3715.1.2.2
		emsEventLogTable OBJECT-TYPE
			SYNTAX SEQUENCE OF EmsEventLogEntry
			ACCESS not-accessible
			STATUS mandatory
			DESCRIPTION
				"A table of active events."
			::= { emsServerEvents 2 }

		
		-- 1.3.6.1.4.1.3715.1.2.2.1
		emsEventLogEntry OBJECT-TYPE
			SYNTAX EmsEventLogEntry
			ACCESS not-accessible
			STATUS mandatory
			DESCRIPTION
				"A row in the eventTable."
			INDEX { eventIndex }
			::= { emsEventLogTable 1 }

		
		EmsEventLogEntry ::=
			SEQUENCE { 
				eventIndex
					INTEGER,
				eventElementType
					DisplayString,
				eventElementIpAddress
					NetworkAddress,
				eventElementName
					DisplayString,
				eventElementLocation
					DisplayString,
				eventGroupId
					INTEGER,
				eventStartTime
					DateAndTime,
				eventSeverity
					INTEGER,
				eventMessage
					DisplayString
			 }

		-- 1.3.6.1.4.1.3715.1.2.2.1.1
		eventIndex OBJECT-TYPE
			SYNTAX INTEGER (1..65536)
			ACCESS read-only
			STATUS mandatory
			DESCRIPTION
				"Index to the eventTable."
			::= { emsEventLogEntry 1 }

		
		-- 1.3.6.1.4.1.3715.1.2.2.1.2
		eventElementType OBJECT-TYPE
			SYNTAX DisplayString
			ACCESS read-only
			STATUS mandatory
			DESCRIPTION
				"Type of the element that initiated this event."
			::= { emsEventLogEntry 2 }

		
		-- 1.3.6.1.4.1.3715.1.2.2.1.3
		eventElementIpAddress OBJECT-TYPE
			SYNTAX NetworkAddress
			ACCESS read-only
			STATUS mandatory
			DESCRIPTION
				"IP address of the element that initiated this event."
			::= { emsEventLogEntry 3 }

		
		-- 1.3.6.1.4.1.3715.1.2.2.1.4
		eventElementName OBJECT-TYPE
			SYNTAX DisplayString
			ACCESS read-only
			STATUS mandatory
			DESCRIPTION
				"Name of the element that initiated the event."
			::= { emsEventLogEntry 4 }

		
		-- 1.3.6.1.4.1.3715.1.2.2.1.5
		eventElementLocation OBJECT-TYPE
			SYNTAX DisplayString
			ACCESS read-only
			STATUS mandatory
			DESCRIPTION
				"Location of the element that initiated the event."
			::= { emsEventLogEntry 5 }

		
		-- 1.3.6.1.4.1.3715.1.2.2.1.6
		eventGroupId OBJECT-TYPE
			SYNTAX INTEGER
			ACCESS read-only
			STATUS mandatory
			DESCRIPTION
				"Common identification for all messages that belong to
				the same event. "
			::= { emsEventLogEntry 6 }

		
		-- 1.3.6.1.4.1.3715.1.2.2.1.7
		eventStartTime OBJECT-TYPE
			SYNTAX DateAndTime
			ACCESS read-only
			STATUS mandatory
			DESCRIPTION
				"Time when the event started."
			::= { emsEventLogEntry 7 }

		
		-- 1.3.6.1.4.1.3715.1.2.2.1.8
		eventSeverity OBJECT-TYPE
			SYNTAX INTEGER
				{
				alarm(1),
				warning(2),
				notification(3)
				}
			ACCESS read-only
			STATUS mandatory
			DESCRIPTION
				"The event's severity level:
				1 = alarm
				2 = warning
				3 = notification"
			::= { emsEventLogEntry 8 }

		
		-- 1.3.6.1.4.1.3715.1.2.2.1.9
		eventMessage OBJECT-TYPE
			SYNTAX DisplayString
			ACCESS read-only
			STATUS mandatory
			DESCRIPTION
				"Verbal description of the event."
			::= { emsEventLogEntry 9 }

		
		-- 1.3.6.1.4.1.3715.1.2.3
		emsEventLogFilters OBJECT IDENTIFIER ::= { emsServerEvents 3 }

		
		-- 1.3.6.1.4.1.3715.1.2.3.3
		alarmFilter OBJECT-TYPE
			SYNTAX INTEGER
				{
				off(1),
				on(2)
				}
			ACCESS read-write
			STATUS optional
			DESCRIPTION
				"A variable for controlling the visibility of alarm
				events on the emsEventLogTable.
				1 = filter off (show warnings)
				2 = filter on (hide warnings)"
			::= { emsEventLogFilters 3 }

		
		-- 1.3.6.1.4.1.3715.1.2.3.4
		warningFilter OBJECT-TYPE
			SYNTAX INTEGER
				{
				off(1),
				on(2)
				}
			ACCESS read-write
			STATUS optional
			DESCRIPTION
				"A variable for controlling the visibility of warning
				events on the emsEventLogTable.
				1 = filter off (show warnings)
				2 = filter on (hide warnings)"
			::= { emsEventLogFilters 4 }

		
		-- 1.3.6.1.4.1.3715.1.2.3.5
		notificationFilter OBJECT-TYPE
			SYNTAX INTEGER
				{
				off(1),
				on(2)
				}
			ACCESS read-write
			STATUS optional
			DESCRIPTION
				"A variable for controlling the visibility of notification
				events on the emsEventLogTable.
				1 = filter off (show notifications)
				2 = filter on (hide notifications)"
			::= { emsEventLogFilters 5 }

		
		-- 1.3.6.1.4.1.3715.1.2.4
		emsTrapControl OBJECT IDENTIFIER ::= { emsServerEvents 4 }

		
		-- 1.3.6.1.4.1.3715.1.2.4.1
		alarmTraps OBJECT-TYPE
			SYNTAX INTEGER
				{
				enabled(1),
				disabled(2)
				}
			ACCESS read-write
			STATUS optional
			DESCRIPTION
				"A variable for controlling the sending of alarm
				traps
				1 = traps enabled
				2 = traps disabled"
			::= { emsTrapControl 1 }

		
		-- 1.3.6.1.4.1.3715.1.2.4.2
		warningTraps OBJECT-TYPE
			SYNTAX INTEGER
				{
				enabled(1),
				disabled(2)
				}
			ACCESS read-write
			STATUS optional
			DESCRIPTION
				"A variable for controlling the sending of warning
				traps
				1 = traps enabled
				2 = traps disabled"
			::= { emsTrapControl 2 }

		
		-- 1.3.6.1.4.1.3715.1.2.4.3
		notificationTraps OBJECT-TYPE
			SYNTAX INTEGER
				{
				enabled(1),
				disabled(2)
				}
			ACCESS read-write
			STATUS optional
			DESCRIPTION
				"A variable for controlling the sending of notification
				traps
				1 = traps enabled
				2 = traps disabled"
			::= { emsTrapControl 3 }

		
		-- 1.3.6.1.4.1.3715.1.2.4.4
		clearedTraps OBJECT-TYPE
			SYNTAX INTEGER
				{
				enabled(1),
				disabled(2)
				}
			ACCESS read-write
			STATUS optional
			DESCRIPTION
				"A variable for controlling the sending of traps on
				cleared events
				1 = traps enabled
				2 = traps disabled"
			::= { emsTrapControl 4 }

		
		-- 1.3.6.1.4.1.3715.1.2.4.9
		trapDelay OBJECT-TYPE
			SYNTAX INTEGER
			ACCESS read-write
			STATUS mandatory
			DESCRIPTION
				"The delay between the occurrence of an event on the EMS
				and the corresponding trap. If the event is cleared within
				the traps delay intervall, the traps is not sent.
				Unit 1 second. Value range 0 to 180.
				"
			::= { emsTrapControl 9 }

		
	
--
-- Trap definitions
--
	
		eventAlarm TRAP-TYPE 
			ENTERPRISE ems
			VARIABLES { eventElementType, eventElementIpAddress, eventElementName, eventElementLocation, eventStartTime, 
				eventMessage, eventGroupId, eventLogMessageID }
			DESCRIPTION 
				"The EMS server has detected a new alarm event."
			::=  1

		eventWarning TRAP-TYPE 
			ENTERPRISE ems
			VARIABLES { eventElementType, eventElementIpAddress, eventElementName, eventElementLocation, eventStartTime, 
				eventMessage, eventGroupId, eventLogMessageID }
			DESCRIPTION 
				"The EMS server has detected a new warning event."
			::=  2

		eventNotification TRAP-TYPE 
			ENTERPRISE ems
			VARIABLES { eventElementType, eventElementIpAddress, eventElementName, eventElementLocation, eventStartTime, 
				eventMessage, eventGroupId, eventLogMessageID }
			DESCRIPTION 
				"The EMS server has detected a new notification event."
			::=  3

		eventCleared TRAP-TYPE 
			ENTERPRISE ems
			VARIABLES { eventElementType, eventElementIpAddress, eventElementName, eventElementLocation, eventStartTime, 
				eventMessage, eventGroupId, eventLogMessageID }
			DESCRIPTION 
				"The EMS server has marked an event as cleared. The
				eventGroupId variable indicates the event(s) that 
				has been cleared."
			::=  4

		serverDown TRAP-TYPE 
			ENTERPRISE ems
			VARIABLES { serverName, serverTimeSinceLastResponse }
			DESCRIPTION 
				"The EMS server has stopped responding."
			::=  9

	
	END

--
-- TELESTE-EMS-MIB.mib
--
