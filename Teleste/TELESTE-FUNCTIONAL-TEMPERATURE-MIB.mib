--
-- TELESTE-FUNCTIONAL-TEMPERATURE-MIB.mib
-- MIB generated by MG-SOFT Visual MIB Builder 2013 (64-bit) Version 9.0  Build 760
-- Wednesday, January 14, 2015 at 12:30:19
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-TEMPERATURE-MIB
-- 
-- Description:   MIB module describing Teleste functional temperature interface specific objects
-- 
-- Revision history:
-- -----------------
-- 3, 14.1.2015 Sami Kuusisto
-- - Added temperatureName.
-- 
-- 2, 13.1.2015 Sami Kuusisto
-- - Added second index to temperatureTable.
-- - Fixed temperatureValue as RO.
-- - Changed indexes.
-- 
-- 1, 9.1.2015 Sami Kuusisto
-- - Initial version.
-- 
-- ****************************************************************************
-- 

	TELESTE-FUNCTIONAL-TEMPERATURE-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.95
		temperature OBJECT IDENTIFIER ::= { functional 95 }

		
		-- 1.3.6.1.4.1.3715.100.95.1
		temperatureTable OBJECT-TYPE
			SYNTAX SEQUENCE OF TemperatureEntry
			ACCESS not-accessible
			STATUS mandatory
			DESCRIPTION
				"A table of temperature elements."
			::= { temperature 1 }

		
		-- 1.3.6.1.4.1.3715.100.95.1.1
		temperatureEntry OBJECT-TYPE
			SYNTAX TemperatureEntry
			ACCESS not-accessible
			STATUS mandatory
			INDEX { functionalModuleId, temperatureIndex }
			::= { temperatureTable 1 }

		
		TemperatureEntry ::=
			SEQUENCE { 
				temperatureIndex
					INTEGER,
				temperatureValue
					INTEGER,
				temperatureStatus
					INTEGER,
				temperatureName
					OCTET STRING
			 }

		-- 1.3.6.1.4.1.3715.100.95.1.1.1
		temperatureIndex OBJECT-TYPE
			SYNTAX INTEGER (1..65535)
			ACCESS read-write
			STATUS mandatory
			::= { temperatureEntry 1 }

		
		-- 1.3.6.1.4.1.3715.100.95.1.1.2
		temperatureValue OBJECT-TYPE
			SYNTAX INTEGER
			ACCESS read-only
			STATUS mandatory
			DESCRIPTION
				"Temperature value. Unit 0.01 oC. 
				
				"
			::= { temperatureEntry 2 }

		
		-- 1.3.6.1.4.1.3715.100.95.1.1.3
		temperatureStatus OBJECT-TYPE
			SYNTAX INTEGER
				{
				temperatureNormal(1),
				temperatureHIHI(2),
				temperatureHi(3),
				temperatureLo(4),
				temperatureLOLO(5)
				}
			ACCESS read-only
			STATUS mandatory
			DESCRIPTION
				"Temperature status:
				1 = normal
				2 = HIHI
				3 = Hi
				4 = Lo
				5 = LOLO"
			::= { temperatureEntry 3 }

		
		-- 1.3.6.1.4.1.3715.100.95.1.1.4
		temperatureName OBJECT-TYPE
			SYNTAX OCTET STRING
			ACCESS read-only
			STATUS mandatory
			DESCRIPTION
				"Human readable name for this temperature object."
			::= { temperatureEntry 4 }

		
	
	END

--
-- TELESTE-FUNCTIONAL-TEMPERATURE-MIB.mib
--
