--
-- TELESTE-PILOTGENERATOR-MIB.mib
-- MIB generated by MG-SOFT Visual MIB Builder Version 4.0 Build 349
-- Tuesday, March 02, 2010 at 09:30:28
--

-- ****************************************************************************
-- Copyright (c) 2007-2010 by:
-- 
-- Teleste Corporation
-- Seponkatu 1
-- FIN-20660 Littoinen, Finland
-- tel. +358 2 2605 611
-- url: http://www.teleste.com
-- 
-- Module Name: TELESTE-PILOTGENERATOR-MIB
-- 
-- Description: MIB module describing pilot generators objects 
--              in Teleste HFC devices
-- 
-- Revision History:
-- -----------------
-- 1.0,  2.3.2010, Matti Susi
-- - first official release
-- 
-- ****************************************************************************
-- 

	TELESTE-PILOTGENERATOR-MIB DEFINITIONS ::= BEGIN
 
		IMPORTS
			OBJECT-TYPE			
				FROM RFC-1212			
			pilotGenerator			
				FROM TELESTE-ROOT-MIB;
	
	
--
-- Node definitions
--
	
		-- 1.3.6.1.4.1.3715.100.3.1
		pilotGeneratorMode OBJECT-TYPE
			SYNTAX INTEGER
				{
				generatorOn(1),
				generatorOff(2),
				generatorRestart(3)
				}
			ACCESS read-write
			STATUS mandatory
			DESCRIPTION
				"Pilot generator mode:
				generatorOn(1)
				generatorOff(2)
				generatorRestart(3)"
			::= { pilotGenerator 1 }

		
		-- 1.3.6.1.4.1.3715.100.3.2
		pilotGeneratorNumberOfPilots OBJECT-TYPE
			SYNTAX INTEGER
			ACCESS read-only
			STATUS mandatory
			DESCRIPTION
				"Number of pilots available in the pilot generator."
			::= { pilotGenerator 2 }
-- Number of pilots to send.
		
-- 
-- 
		-- 1.3.6.1.4.1.3715.100.3.3
		pilotGeneratorPilotDuration OBJECT-TYPE
			SYNTAX INTEGER
			ACCESS read-write
			STATUS mandatory
			DESCRIPTION
				"The time each pilot is ON. Unit 0.01 seconds."
			::= { pilotGenerator 3 }

		
		-- 1.3.6.1.4.1.3715.100.3.10
		pilotGeneratorPilotTable OBJECT-TYPE
			SYNTAX SEQUENCE OF PilotGeneratorPilotEntry
			ACCESS not-accessible
			STATUS mandatory
			DESCRIPTION
				"Table of pilots."
			::= { pilotGenerator 10 }

		
		-- 1.3.6.1.4.1.3715.100.3.10.1
		pilotGeneratorPilotEntry OBJECT-TYPE
			SYNTAX PilotGeneratorPilotEntry
			ACCESS not-accessible
			STATUS mandatory
			INDEX { pilotIndex }
			::= { pilotGeneratorPilotTable 1 }

		
		PilotGeneratorPilotEntry ::=
			SEQUENCE { 
				pilotIndex
					INTEGER,
				pilotMode
					INTEGER,
				pilotFrequency
					INTEGER,
				pilotLevel
					INTEGER
			 }

		-- 1.3.6.1.4.1.3715.100.3.10.1.1
		pilotIndex OBJECT-TYPE
			SYNTAX INTEGER (2..50)
			ACCESS read-only
			STATUS mandatory
			DESCRIPTION
				"Pilot index."
			::= { pilotGeneratorPilotEntry 1 }

		
		-- 1.3.6.1.4.1.3715.100.3.10.1.2
		pilotMode OBJECT-TYPE
			SYNTAX INTEGER
				{
				pilotOn(1),
				pilotOff(2),
				pilotRestart(3)
				}
			ACCESS read-write
			STATUS mandatory
			DESCRIPTION
				"Pilot mode:
				pilotOn(1)
				pilotOff(2)
				pilotRestart(3)"
			::= { pilotGeneratorPilotEntry 2 }

		
		-- 1.3.6.1.4.1.3715.100.3.10.1.3
		pilotFrequency OBJECT-TYPE
			SYNTAX INTEGER
			ACCESS read-write
			STATUS mandatory
			DESCRIPTION
				"Pilot frequency. Unit 0.01 MHz."
			::= { pilotGeneratorPilotEntry 3 }

		
		-- 1.3.6.1.4.1.3715.100.3.10.1.4
		pilotLevel OBJECT-TYPE
			SYNTAX INTEGER
			ACCESS read-write
			STATUS mandatory
			DESCRIPTION
				"Pilot level. Unit 0.01 dBuV."
			::= { pilotGeneratorPilotEntry 4 }

		
	
	END

--
-- TELESTE-PILOTGENERATOR-MIB.mib
--
