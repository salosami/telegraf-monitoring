--
-- TELESTE-FUNCTIONAL-ALSC-MIB.mib
-- MIB generated by MG-SOFT Visual MIB Builder 2021 (64-bit) Version 15.00  Build 1510
-- Wednesday, September 08, 2021 at 13:34:47
--

-- ****************************************************************************
-- Copyright (c) 2003-2012 by:
-- 
-- Teleste Corporation
-- Seponkatu 1
-- FIN-20660 Littoinen, Finland
-- tel. +358 2 2605 611
-- url: http://www.teleste.com
-- 
-- Module Name:   TELESTE-FUNCTIONAL-ALSC-MIB
-- 
-- Description:   MIB module describing Teleste functional AL(S)C interface specific objects
-- 
-- Revision history:
-- -----------------
-- 8, 8.9.2021, Sami Kuusisto
-- - Added alscGainAndSlopeControlState.
-- 
-- 7, 5.6.2014, Sami Kuusisto
-- - Added value ranges.
-- 
-- 6, 19.5.2014, Sami Kuusisto
-- - Changed alscControl enumeration to match TSEMP enumerations.
-- 
-- 5, 18.3.2014, Sami Kuusisto
-- - Fixed numbering
-- 
-- 4, 18.3.2014, Sami Kuusisto
-- - Added alscControlStatus
-- 
-- 3, 18.3.2014, Sami Kuusisto
-- - Added alscPilotsStatus and alscControlsStatus.
-- 
-- 2, 14.3.2014, Sami Kuusisto
-- - Chnaged alscStatus type and description
-- 
-- 1, 10.3.2014, Sami Kuusisto
-- - Initial version.
-- 
-- ****************************************************************************
-- 

	TELESTE-FUNCTIONAL-ALSC-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.75
		alsc OBJECT IDENTIFIER ::= { functional 75 }

		
		-- 1.3.6.1.4.1.3715.100.75.1
		alscControl OBJECT-TYPE
			SYNTAX INTEGER
				{
				modeManual(1),
				modeIntelligent(2),
				modeALSC(3),
				modeALC(4),
				modeOLC(5),
				modeReserved(6)
				}
			ACCESS read-write
			STATUS mandatory
			DESCRIPTION
				"AL(S)C operating mode:
				1 = AL(S)C off; gain and slope are in manual control.
				2 = Total gain is adjusted manually, individual gain control elements
				    are adjusted automatically based on it. Slope controls are adjusted manually.
				3 = ALSC(+OLC) on: gain and slope controls are adjusted automatically based on pilot levels.
				4 = ALC(+OLC) on: gain controls are adjusted automatically based on pilot levels. Slope controls are adjusted manually.
				5 = Optical Level Control (OLC) mode. Gain and slope controls are adjusted manually.
				6 = reserved for future use/for compability reasons."
			::= { alsc 1 }

		
		-- 1.3.6.1.4.1.3715.100.75.2
		alscControlStatus OBJECT-TYPE
			SYNTAX INTEGER
				{
				alscControlStatusOn(1),
				alscControlStatusOff(2),
				alscControlStatusOnButNoHw(3),
				alscControlStatusOffAndNoHw(4)
				}
			ACCESS read-only
			STATUS mandatory
			DESCRIPTION
				"ALSC control status
				1: ALSC is on/enabled and running
				2: ALSC is switched off by user
				3: ALSC is switched on by user, but HW doesn't support ALSC (currently)
				4: ALSC is switched off by user and there's no HW that supports ALSC (currently)
				"
			::= { alsc 2 }

		
		-- 1.3.6.1.4.1.3715.100.75.3
		alscStatus OBJECT-TYPE
			SYNTAX INTEGER
			ACCESS read-only
			STATUS mandatory
			DESCRIPTION
				"ALSC status (bitfield)
				0x0001: all ok (this is set only if all others are reset)
				0x0002: alsc disabled (by user)
				0x0004: alsc disabled (by esw; no transponder)
				0x0008: main pilot(s) missing
				0x0010: 1 pilot only
				0x0020: all pilots missing
				0x0100: pilot measurement problem (below lost level, illegal freq, measurement error etc.)
				0x0200: reserved
				0x0400: alsc disabled: hardware error
				0x0800: reserved, 0x1000: reserved, 0x2000: reserved, 0x4000: reserved, 0x8000: reserved"
			::= { alsc 3 }

		
		-- 1.3.6.1.4.1.3715.100.75.4
		alscPilotsStatus OBJECT-TYPE
			SYNTAX INTEGER
				{
				alscPilotsStatusOk(1),
				alscPilotsStatusMainPilotsMissing(2),
				alscPilotsStatusOnePilotOnly(3),
				alscPilotsStatusAllPilotsMissing(4),
				alscPilotsStatusError(5),
				alscPilotsStatusOther(6),
				alscPilotsStatusUnknown(7),
				alscPilotsStatusNA(8)
				}
			ACCESS read-only
			STATUS mandatory
			DESCRIPTION
				"AL(S)C pilots status
				1: All pilots ok
				2: High, low or both main pilots missing
				3: ALSC operates on 1 pilot only
				4: All pilots missing, ALSC operates based on alscPilotLostAction
				5: ALSC has some error
				6: ALSC state other
				7: ALSC state unknown
				8: ALSC state not available"
			::= { alsc 4 }

		
		-- 1.3.6.1.4.1.3715.100.75.5
		alscControlsStatus OBJECT-TYPE
			SYNTAX INTEGER
				{
				alscControlsStatusOk(1),
				alscControlsStatusSaturated(2)
				}
			ACCESS read-only
			STATUS mandatory
			DESCRIPTION
				"ALSC controls status
				1: All controls ok
				2: One or more controls saturated. See alscLevelControlStatus."
			::= { alsc 5 }

		
		-- 1.3.6.1.4.1.3715.100.75.6
		alscPilotLostAction OBJECT-TYPE
			SYNTAX INTEGER
				{
				freeze(1),
				preset(2)
				}
			ACCESS read-write
			STATUS mandatory
			DESCRIPTION
				"ALSC behaviour when all pilots are lost.
				1 = freeze gain and slope to current values
				2 = set gain and slope to preset values (alscLevelControlDefaultValue)"
			::= { alsc 6 }

		
		-- 1.3.6.1.4.1.3715.100.75.7
		alscTargetLevelTable OBJECT-TYPE
			SYNTAX SEQUENCE OF AlscTargetLevelEntry
			ACCESS not-accessible
			STATUS mandatory
			DESCRIPTION
				"A table of ALSC target levels entries."
			::= { alsc 7 }

		
		-- 1.3.6.1.4.1.3715.100.75.7.1
		alscTargetLevelEntry OBJECT-TYPE
			SYNTAX AlscTargetLevelEntry
			ACCESS not-accessible
			STATUS mandatory
			INDEX { functionalModuleId }
			::= { alscTargetLevelTable 1 }

		
		AlscTargetLevelEntry ::=
			SEQUENCE { 
				alscTargetLevelValue
					INTEGER,
				alscTargetLevelStatus
					INTEGER,
				alscTargetLevelBackoff
					INTEGER,
				alscTargetLevelPrevAmp
					INTEGER
			 }

		-- 1.3.6.1.4.1.3715.100.75.7.1.1
		alscTargetLevelValue OBJECT-TYPE
			SYNTAX INTEGER (0..20000)
			ACCESS read-write
			STATUS mandatory
			DESCRIPTION
				"Pilot target level value. Unit 0.01 dBuV."
			::= { alscTargetLevelEntry 1 }

		
		-- 1.3.6.1.4.1.3715.100.75.7.1.2
		alscTargetLevelStatus OBJECT-TYPE
			SYNTAX INTEGER
				{
				useActive(1),
				useStandby(2),
				useDisabled(3),
				useLost(4),
				useActiveAndControlGain(5),
				useActiveAndControlSlope(6),
				useUnknown(7),
				useFailure(8)
				}
			ACCESS read-only
			STATUS mandatory
			DESCRIPTION
				"This object tells if the pilot is used for ALSC or not.
				1 = Pilot is in use and controlling ALSC
				2 = Pilot is not in use (backup or missing)
				3 = Pilot is disabled
				4 = Pilot is lost
				5 = Pilot is in use and controlling gain 
				6 = Pilot is in use and controlling slope
				7 = Pilot usage unknown
				8 = Pilot failure: illegal frequency, too high/low measurement, hardware error etc."
			::= { alscTargetLevelEntry 2 }

		
		-- 1.3.6.1.4.1.3715.100.75.7.1.3
		alscTargetLevelBackoff OBJECT-TYPE
			SYNTAX INTEGER (-1500..500)
			ACCESS read-write
			STATUS mandatory
			DESCRIPTION
				"Pilot target level backoff value. 
				Unit 0.01 dB."
			::= { alscTargetLevelEntry 3 }

		
		-- 1.3.6.1.4.1.3715.100.75.7.1.4
		alscTargetLevelPrevAmp OBJECT-TYPE
			SYNTAX INTEGER (0..20000)
			ACCESS read-write
			STATUS mandatory
			DESCRIPTION
				"Pilot target level value of the previous amplifier in cascade. 
				Unit 0.01 dBuV."
			::= { alscTargetLevelEntry 4 }

		
		-- 1.3.6.1.4.1.3715.100.75.8
		alscLevelControlTable OBJECT-TYPE
			SYNTAX SEQUENCE OF AlscLevelControlEntry
			ACCESS not-accessible
			STATUS mandatory
			DESCRIPTION
				"A table of level control element specific options."
			::= { alsc 8 }

		
		-- 1.3.6.1.4.1.3715.100.75.8.1
		alscLevelControlEntry OBJECT-TYPE
			SYNTAX AlscLevelControlEntry
			ACCESS not-accessible
			STATUS mandatory
			INDEX { functionalModuleId }
			::= { alscLevelControlTable 1 }

		
		AlscLevelControlEntry ::=
			SEQUENCE { 
				alscLevelControlDefaultValue
					INTEGER,
				alscLevelControlStatus
					INTEGER
			 }

		-- 1.3.6.1.4.1.3715.100.75.8.1.1
		alscLevelControlDefaultValue OBJECT-TYPE
			SYNTAX INTEGER
			ACCESS read-write
			STATUS mandatory
			DESCRIPTION
				"'Go to' value used when all pilots are lost.
				Unit 0.01 dB."
			::= { alscLevelControlEntry 1 }

		
		-- 1.3.6.1.4.1.3715.100.75.8.1.2
		alscLevelControlStatus OBJECT-TYPE
			SYNTAX INTEGER
				{
				alscLevelControlStatusNormal(1),
				alscLevelControlStatusMinimum(2),
				alscLevelControlStatusMaximum(3),
				alscLevelControlStatusFrozen(4),
				alscLevelControlStatusDefault(5),
				alscLevelControlStatusSaturatedAtMinimum(6),
				alscLevelControlStatusSaturatedAtMaximum(7)
				}
			ACCESS read-write
			STATUS mandatory
			DESCRIPTION
				"Gain control status:
				1 = normal
				2 = minimum (control at minimum, but no request to adjust under minimum)
				3 = maximum (control at maximum, but no request to adjust over maximum)
				4 = frozen (ALSC on but no pilots are detected)
				5 = default (ALSC on but no pilots are detected)
				6 = saturatedAtMinimum (control saturated at minimum value, but there's need to adjust under minimum)
				7 = saturatedAtMaximum (control saturated at maximum value, but there's need to adjust over maximum)
				
				This object has an entry in the discretePropertyTable.
				
				Returns value normal(1) when ALSC is not enabled."
			::= { alscLevelControlEntry 2 }

		
		-- 1.3.6.1.4.1.3715.100.75.9
		alscGainAndSlopeControlState OBJECT-TYPE
			SYNTAX INTEGER
			ACCESS read-only
			STATUS mandatory
			DESCRIPTION
				"ALSC gain and slope control state.

				
				0xSSGG, where GG is gain status and SS is slope status.
				
0x0001: Gain is not adjusted by ALSC currently (STOP).
				
0x0002: Gain is adjusted by ALSC currently (UP).

				0x0004: Gain is adjusted by ALSC currently (DOWN).
				
0x0080...0x0008: reserved
				
0x0100: Slope is not adjusted by ALSC currently (STOP).
				
0x0200: Slope is adjusted by ALSC currently (UP).
				
0x0400: Slope is adjusted by ALSC currently (DOWN).
				
0x8000...0x0800: reserved
				"
			::= { alsc 9 }

		
	
	END

--
-- TELESTE-FUNCTIONAL-ALSC-MIB.mib
--
