--
-- TELESTE-CXENODE-MIB.mib
-- MIB generated by MG-SOFT Visual MIB Builder 2013 (64-bit) Version 9.0  Build 720
-- Thursday, October 24, 2013 at 16:03:42
--

-- ****************************************************************************
-- Copyright (c) 2005-2013 by:
-- 
-- Teleste Corporation
-- Telestenkatu 1
-- FIN-20660 Littoinen, Finland
-- tel. +358 2 2605 611
-- url: http://www.teleste.com
-- 
-- Description: CXE node definitions
-- 
-- Revision History:
-- -----------------
-- 5, 24.10.2013, Sami Halen
-- - renamed TELESTE-CXE85X-MIB to TELESTE-CXENODE-MIB
-- - added cxeStateLocalUiActive
-- - added cxeRfSlopeAnalog
-- - renamed cxeRfSlope to cxeRfSlopeDiscrete
-- 
-- 4, 24.4.2013, Sami Halen
-- - added value middle(3) to cxeRfSlope
-- - added cxeOpticalInputPowerReference and cxeOpticalInput2PowerReference
-- 
-- 3, 3.7.2012, Sami Halen
-- - added cxeStateExtCtrlActivated
-- 
-- 2, 20.3.2012, Sami Halen
-- - changed name from cxe850 to cxe85x
-- - added objects for CXE852: cxeOpticalInput2Power, cxeOpticalInputSelection,
--   cxeActiveOpticalInput, cxeStateBackupActivated, cxeStateRfOutput,
--   cxeExtCtrlTimeout, cxeExtCtrlLength
-- - some cleanup & clarifications
-- 
-- 1, 4.3.2010 Rainer Salminen and Sami Salo
-- - first official version
--  
-- ****************************************************************************

	TELESTE-CXENODE-MIB DEFINITIONS ::= BEGIN
 
		IMPORTS
			OBJECT-TYPE			
				FROM RFC-1212			
			IpAddress			
				FROM RFC1155-SMI			
			cxeNode			
				FROM TELESTE-CXX-MIB;
	
	
--
-- Node definitions
--
	
		-- 1.3.6.1.4.1.3715.18.850.1
		cxeStateInternalError OBJECT-TYPE
			SYNTAX INTEGER
				{
				noError(1),
				error(2)
				}
			ACCESS read-only
			STATUS mandatory
			DESCRIPTION
				"Serious device hardware or software error.
				Discrete property."
			::= { cxeNode 1 }

		
		-- 1.3.6.1.4.1.3715.18.850.2
		cxeStatePowerSupply OBJECT-TYPE
			SYNTAX INTEGER
				{
				stateOK(1),
				stateError(2)
				}
			ACCESS read-only
			STATUS mandatory
			DESCRIPTION
				"Status of the power supply.
				Discrete property."
			::= { cxeNode 2 }

		
		-- 1.3.6.1.4.1.3715.18.850.3
		cxeStateSettingsChanged OBJECT-TYPE
			SYNTAX INTEGER
				{
				settingsNotChanged(1),
				settingsChanged(2)
				}
			ACCESS read-only
			STATUS mandatory
			DESCRIPTION
				"Device settings changed. 
				Value settingsChanged(2) is active approximately one minute 
				after last change of device setting.
				Discrete property."
			::= { cxeNode 3 }

		
		-- 1.3.6.1.4.1.3715.18.850.4
		cxeStateApplicationStarted OBJECT-TYPE
			SYNTAX INTEGER
				{
				appRunning(1),
				appStarting(2)
				}
			ACCESS read-only
			STATUS mandatory
			DESCRIPTION
				"State appStarting(2) is active approximately one minute after device start.
				Discrete property."
			::= { cxeNode 4 }

		
		-- 1.3.6.1.4.1.3715.18.850.5
		cxeOpticalInputPower OBJECT-TYPE
			SYNTAX INTEGER
			ACCESS read-only
			STATUS mandatory
			DESCRIPTION
				"Optical input power. Unit 0.1 dBm.
				Analog property."
			::= { cxeNode 5 }

		
		-- 1.3.6.1.4.1.3715.18.850.6
		cxeRfAdjustmentMode OBJECT-TYPE
			SYNTAX INTEGER
				{
				adjHw(1),
				adjSwManualSettings(2),
				adjSwOmi(3)
				}
			ACCESS read-write
			STATUS mandatory
			DESCRIPTION
				"RF settings adjustment mode:
				1 = hardware adjustment
				2 = software/manual adjustment
				3 = software/OMI adjustment"
			::= { cxeNode 6 }

		
		-- 1.3.6.1.4.1.3715.18.850.7
		cxeRfGain OBJECT-TYPE
			SYNTAX INTEGER
			ACCESS read-write
			STATUS mandatory
			DESCRIPTION
				"RF gain value. Unit 1 dB."
			::= { cxeNode 7 }

		
		-- 1.3.6.1.4.1.3715.18.850.8
		cxeRfSlopeDiscrete OBJECT-TYPE
			SYNTAX INTEGER
				{
				flat(1),
				high(2),
				middle(3)
				}
			ACCESS read-write
			STATUS mandatory
			DESCRIPTION
				"RF slope discrete setting:
				1 = flat
				2 = high slope
				3 = middle slope"
			::= { cxeNode 8 }

		
		-- 1.3.6.1.4.1.3715.18.850.9
		cxeEnableOLC OBJECT-TYPE
			SYNTAX INTEGER
				{
				disable(1),
				enable(2)
				}
			ACCESS read-write
			STATUS mandatory
			DESCRIPTION
				"Optical level control (OLC)
				1 = OLC disabled
				2 = OLC enabled"
			::= { cxeNode 9 }

		
		-- 1.3.6.1.4.1.3715.18.850.10
		cxeTransmitterOMI OBJECT-TYPE
			SYNTAX INTEGER
			ACCESS read-write
			STATUS mandatory
			DESCRIPTION
				"Transmitter OMI value for gain calculation. Unit 0.1 %."
			::= { cxeNode 10 }

		
		-- 1.3.6.1.4.1.3715.18.850.11
		cxeStateSwOmiCalc OBJECT-TYPE
			SYNTAX INTEGER
				{
				calcVoid(1),
				calcBad(2),
				calcGood(3)
				}
			ACCESS read-write
			STATUS mandatory
			DESCRIPTION
				"Gain calculation status in 'software/OMI' adjustment mode. 
				1 = not in software/OMI mode
				2 = calculated gain out of adjustment range
				3 = calculated gain within adjustment range"
			::= { cxeNode 11 }

		
		-- 1.3.6.1.4.1.3715.18.850.12
		cxeRfOutputTargetLevel OBJECT-TYPE
			SYNTAX INTEGER
			ACCESS read-write
			STATUS mandatory
			DESCRIPTION
				"Target output level for gain calculation. Unit 1 dBµV."
			::= { cxeNode 12 }

		
		-- 1.3.6.1.4.1.3715.18.850.13
		cxeRfOutputPower OBJECT-TYPE
			SYNTAX INTEGER
			ACCESS read-only
			STATUS mandatory
			DESCRIPTION
				"RF output power. Unit 0.1 dBm.
				Analog property."
			::= { cxeNode 13 }

		
		-- 1.3.6.1.4.1.3715.18.850.14
		cxeCmdReferenceRF OBJECT-TYPE
			SYNTAX INTEGER
				{
				noReferenceChange(1),
				storeReference(2),
				factoryReference(3)
				}
			ACCESS read-write
			STATUS mandatory
			DESCRIPTION
				"Command to set RF output power reference level.
				1 = no action, always returned on reads
				2 = set current RF output power reference level to current output power value.
				    Enables all alarm limits and sets them to +-3 and +-6 dB from 
				    the reference value.
				3 = set the reference level and alarm limits to factory defaults."
			::= { cxeNode 14 }

		
		-- 1.3.6.1.4.1.3715.18.850.15
		cxeCmdReset OBJECT-TYPE
			SYNTAX INTEGER
				{
				noReset(1),
				communicationReset(2),
				factoryReset(3)
				}
			ACCESS read-write
			STATUS mandatory
			DESCRIPTION
				"Command to reset device settings to factory defaults.
				1 = no action, always returned on reads
				2 = reset communication settings to factory defaults
				3 = reset all settings to factory defaults"
			::= { cxeNode 15 }

		
		-- 1.3.6.1.4.1.3715.18.850.16
		cxeEthernetStatus OBJECT-TYPE
			SYNTAX INTEGER
			ACCESS read-write
			STATUS mandatory
			DESCRIPTION
				"Ethernet status. Bit field:
				0x0400 = Link is 100Mbps
				0x0200 = Link is full duplex mode 
				0x0020 = PHY link is up"
			::= { cxeNode 16 }

		
		-- 1.3.6.1.4.1.3715.18.850.17
		cxeIpAddrConfigMode OBJECT-TYPE
			SYNTAX INTEGER
				{
				manual(1),
				dhcp(2)
				}
			ACCESS read-write
			STATUS mandatory
			DESCRIPTION
				"IP addressing mode:
				1 = manual
				2 = DHCP / AutoIP"
			::= { cxeNode 17 }

		
		-- 1.3.6.1.4.1.3715.18.850.18
		cxeIpAddress OBJECT-TYPE
			SYNTAX IpAddress
			ACCESS read-only
			STATUS mandatory
			DESCRIPTION
				"Current IP address."
			::= { cxeNode 18 }

		
		-- 1.3.6.1.4.1.3715.18.850.19
		cxeIpMask OBJECT-TYPE
			SYNTAX IpAddress
			ACCESS read-only
			STATUS mandatory
			DESCRIPTION
				"Current IP subnet mask."
			::= { cxeNode 19 }

		
		-- 1.3.6.1.4.1.3715.18.850.20
		cxeIpGateway OBJECT-TYPE
			SYNTAX IpAddress
			ACCESS read-only
			STATUS mandatory
			DESCRIPTION
				"Current IP gateway."
			::= { cxeNode 20 }

		
		-- 1.3.6.1.4.1.3715.18.850.21
		cxeManualIpAddress OBJECT-TYPE
			SYNTAX IpAddress
			ACCESS read-write
			STATUS mandatory
			DESCRIPTION
				"IP address used in manual mode."
			::= { cxeNode 21 }

		
		-- 1.3.6.1.4.1.3715.18.850.22
		cxeManualIpMask OBJECT-TYPE
			SYNTAX IpAddress
			ACCESS read-write
			STATUS mandatory
			DESCRIPTION
				"IP subnet mask used in manual mode."
			::= { cxeNode 22 }

		
		-- 1.3.6.1.4.1.3715.18.850.23
		cxeManualIpGateway OBJECT-TYPE
			SYNTAX IpAddress
			ACCESS read-write
			STATUS mandatory
			DESCRIPTION
				"IP gateway used in manual mode."
			::= { cxeNode 23 }

		
		-- 1.3.6.1.4.1.3715.18.850.24
		cxeReadCommunity OBJECT-TYPE
			SYNTAX OCTET STRING
			ACCESS read-write
			STATUS mandatory
			DESCRIPTION
				"Read community used in SNMP communication."
			::= { cxeNode 24 }

		
		-- 1.3.6.1.4.1.3715.18.850.25
		cxeWriteCommunity OBJECT-TYPE
			SYNTAX OCTET STRING
			ACCESS read-write
			STATUS mandatory
			DESCRIPTION
				"Write community used in SNMP communication."
			::= { cxeNode 25 }

		
		-- 1.3.6.1.4.1.3715.18.850.100
		cxeOpticalInput2Power OBJECT-TYPE
			SYNTAX INTEGER
			ACCESS read-only
			STATUS mandatory
			DESCRIPTION
				"Optical input power for receiver 2. Unit 0.1 dBm.
				Analog property."
			::= { cxeNode 100 }

		
		-- 1.3.6.1.4.1.3715.18.850.101
		cxeOpticalInputSelection OBJECT-TYPE
			SYNTAX INTEGER
				{
				manual1(1),
				manual2(2),
				automatic(3)
				}
			ACCESS read-write
			STATUS mandatory
			DESCRIPTION
				"Input selection mode:
				1 = manual, input 1
				2 = manual, input 2
				3 = automatic"
			::= { cxeNode 101 }

		
		-- 1.3.6.1.4.1.3715.18.850.102
		cxeActiveOpticalInput OBJECT-TYPE
			SYNTAX INTEGER
				{
				input1(1),
				input2(2)
				}
			ACCESS read-only
			STATUS mandatory
			DESCRIPTION
				"Active optical input:
				1 = input 1
				2 = input 2"
			::= { cxeNode 102 }

		
		-- 1.3.6.1.4.1.3715.18.850.103
		cxeStateBackupActivated OBJECT-TYPE
			SYNTAX INTEGER
				{
				noBackup(1),
				backupActivated(2)
				}
			ACCESS read-only
			STATUS mandatory
			DESCRIPTION
				"Automatic backup activated.
				Discrete property."
			::= { cxeNode 103 }

		
		-- 1.3.6.1.4.1.3715.18.850.104
		cxeStateRfOutput OBJECT-TYPE
			SYNTAX INTEGER
				{
				rfOutputOk(1),
				rfOutputMissing(2)
				}
			ACCESS read-only
			STATUS mandatory
			DESCRIPTION
				"RF output status.
				Discrete property."
			::= { cxeNode 104 }

		
		-- 1.3.6.1.4.1.3715.18.850.110
		cxeOpticalInputPowerReference OBJECT-TYPE
			SYNTAX INTEGER
			ACCESS read-write
			STATUS mandatory
			DESCRIPTION
				"Optical input power reference value. Unit 0.1 dBm."
			::= { cxeNode 110 }

		
		-- 1.3.6.1.4.1.3715.18.850.111
		cxeOpticalInput2PowerReference OBJECT-TYPE
			SYNTAX INTEGER
			ACCESS read-write
			STATUS mandatory
			DESCRIPTION
				"Optical input power reference value for receiver 2. Unit 0.1 dBm."
			::= { cxeNode 111 }

		
		-- 1.3.6.1.4.1.3715.18.850.150
		cxeExtCtrlTimeout OBJECT-TYPE
			SYNTAX INTEGER
			ACCESS read-write
			STATUS mandatory
			DESCRIPTION
				"Timeout for activating the 'external control' output. Unit 1 s.
				0 = disabled"
			::= { cxeNode 150 }

		
		-- 1.3.6.1.4.1.3715.18.850.151
		cxeExtCtrlLength OBJECT-TYPE
			SYNTAX INTEGER
			ACCESS read-write
			STATUS mandatory
			DESCRIPTION
				"Length of 'external control' output activation. Unit 1 s.
				0 = activate manually"
			::= { cxeNode 151 }

		
		-- 1.3.6.1.4.1.3715.18.850.152
		cxeStateExtCtrlActivated OBJECT-TYPE
			SYNTAX INTEGER
				{
				extCtrlNotActivated(1),
				extCtrlActivated(2)
				}
			ACCESS read-only
			STATUS mandatory
			DESCRIPTION
				"External control output activated.
				Discrete property."
			::= { cxeNode 152 }

		
		-- 1.3.6.1.4.1.3715.18.850.200
		cxeStateLocalUiActive OBJECT-TYPE
			SYNTAX INTEGER
				{
				notActive(1),
				active(2)
				}
			ACCESS read-only
			STATUS mandatory
			DESCRIPTION
				"Local configuration session in action.
				Discrete property."
			::= { cxeNode 200 }

		
		-- 1.3.6.1.4.1.3715.18.850.201
		cxeRfSlopeAnalog OBJECT-TYPE
			SYNTAX INTEGER
			ACCESS read-write
			STATUS mandatory
			DESCRIPTION
				"RF slope analog value. Unit 1 dB."
			::= { cxeNode 201 }

		
	
	END

--
-- TELESTE-CXENODE-MIB.mib
--
