--
-- TELESTE-FUNCTIONAL-ACCESSORIES-MIB.mib
-- MIB generated by MG-SOFT Visual MIB Builder 2021 (64-bit) Version 15.00  Build 1510
-- Thursday, May 05, 2022 at 15:12:22
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-ACCESSORIES-MIB
-- 
-- Description:   MIB module describing Teleste functional accessories interface specific objects
-- 
-- Revision history:
-- -----------------
-- 19, 5.5.2022, Sami Kuusisto
-- - Added enums fro AC630 and AC631 to universalPluginType.
-- 
-- 18, 12.10.2020, Sami Kuusisto
-- - Added inputOutputModuleTable.
-- 
-- 17, 9.9.2020, Sami Kuusisto
-- - Added new diplexFilterTypes: ICON62xx.
-- 
-- 16, 24.5.2019, Sami Kuusisto
-- - Added TXX2C2v2 plugin type to universalPluginType. Changed TXX4C1v2 enum by +1.
-- 
-- 15, 24.5.2019, Sami Kuusisto
-- - Added TXX4C1v2 plugin type to universalPluginType.
-- 
-- 14, 20.12.2018, Sami Kuusisto
-- - Added new enums diplexFilterTypeCXF117, diplexFilterTypeCXF042 and diplexFilterTypeCXTXXX to diplexFilterType.
-- 
-- 13, 19.1.2018, Sami Kuusisto
-- - Added TXX2C1v2 plugin type to universalPluginType.
-- 
-- 12, 1.3.2017, Sami Kuusisto
-- - Renamed TXS016v2 to TXS015v2 (universalPluginType).
-- 
-- 11, 15.2.2017, Sami Kuusisto
-- - Added TXX1G2v2 plugin type to universalPluginType.
-- 
-- 10, 6.2.2017, Sami Kuusisto
-- - Added TXS016v2 plugin type to universalPluginType.
-- 
-- 9, 24.8.2015, Sami Kuusisto
-- - Added TXX258v2, TXS004v2, TXS008v2 and TXS012v2 plugin type to universalPluginType.
-- 
-- 8, 17.5.2016, Sami Kuusisto
-- - Added TXX258 plugin type to universalPluginType.
-- 
-- 7, 8.1.2016, Sami Kuusisto
-- - Added new universal plug types.
-- 
-- 6, 30.9.2015, Sami Kuusisto
-- - Fixed diplexFilterTypeCXF200 to diplexFilterTypeCXF204.
-- 
-- 5, 21.8.2014, Sami Kuusisto
-- - Fixed passiveName syntax type from integer to octet string.
-- 
-- 4, 5.6.2014, Sami Kuusisto
-- - Fixed typo.
-- 
-- 3, 2.4.2014, Sami Kuusisto
-- - fixed typo in voltagesEntry.
-- 
-- 2, 13.3.2014, Sami Kuusisto
-- - Changed universalPluginType enumeration.
-- 
-- 1, 12.3.2014, Sami Kuusisto
-- - Initial version.
-- 
-- ****************************************************************************
-- 

	TELESTE-FUNCTIONAL-ACCESSORIES-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.96
		accessories OBJECT IDENTIFIER ::= { functional 96 }

		
		-- 1.3.6.1.4.1.3715.100.96.1
		diplexFilterTable OBJECT-TYPE
			SYNTAX SEQUENCE OF DiplexFilterEntry
			ACCESS not-accessible
			STATUS mandatory
			::= { accessories 1 }

		
		-- 1.3.6.1.4.1.3715.100.96.1.1
		diplexFilterEntry OBJECT-TYPE
			SYNTAX DiplexFilterEntry
			ACCESS not-accessible
			STATUS mandatory
			INDEX { functionalModuleId }
			::= { diplexFilterTable 1 }

		
		DiplexFilterEntry ::=
			SEQUENCE { 
				diplexFilterType
					INTEGER
			 }

		-- 1.3.6.1.4.1.3715.100.96.1.1.1
		diplexFilterType OBJECT-TYPE
			SYNTAX INTEGER
				{
				diplexFilterTypeShort(1),
				diplexFilterTypeCXF065(2),
				diplexFilterTypeCXF085(4),
				diplexFilterTypeCXF204(6),
				diplexFilterTypeCXF117(8),
				diplexFilterTypeCXF042(9),
				diplexFilterTypeCXTXXX(10),
				diplexFilterTypeOpen(12),
				diplexFilterTypeReserved(13),
				diplexFilterTypeUnknown(14),
				diplexFilterTypeNA(15),
				diplexFilterTypeICON6246(26),
				diplexFilterTypeICON6250(30),
				diplexFilterTypeICON6251(31),
				diplexFilterTypeICON6253(32),
				diplexFilterTypeICON6255(33),
				diplexFilterTypeICON6257(34),
				diplexFilterTypeICON6242(36)
				}
			ACCESS read-only
			STATUS mandatory
			DESCRIPTION
				"Diplex filter type. 
				1: short, 
				2: CXF065, ICON6243
				4: CXF085, ICON6245
				6: CXF204, ICON6249
				8: CXF117,
				9: CXF042, ICON6241
				10: CXTXXX,
				12: open, 
				13: reserved, 
				14: unknown,
				15: N/A,
				26: ICON6246,
				30: ICON6250,
				31: ICON6251,
				32: ICON6253,
				33: ICON6255,
				34: ICON6257, 
				36: ICON6242"
			::= { diplexFilterEntry 1 }

		
		-- 1.3.6.1.4.1.3715.100.96.2
		passivesTable OBJECT-TYPE
			SYNTAX SEQUENCE OF PassivesEntry
			ACCESS not-accessible
			STATUS mandatory
			::= { accessories 2 }

		
		-- 1.3.6.1.4.1.3715.100.96.2.1
		passivesEntry OBJECT-TYPE
			SYNTAX PassivesEntry
			ACCESS not-accessible
			STATUS mandatory
			DESCRIPTION
				"A table of passive texts."
			INDEX { functionalModuleId }
			::= { passivesTable 1 }

		
		PassivesEntry ::=
			SEQUENCE { 
				passiveName
					OCTET STRING
			 }

		-- 1.3.6.1.4.1.3715.100.96.2.1.1
		passiveName OBJECT-TYPE
			SYNTAX OCTET STRING (SIZE (0..12))
			ACCESS read-write
			STATUS mandatory
			DESCRIPTION
				"User editable name of passive module.
				The lenght of name is device dependent. Device truncates oversized names."
			::= { passivesEntry 1 }

		
		-- 1.3.6.1.4.1.3715.100.96.3
		voltagesTable OBJECT-TYPE
			SYNTAX SEQUENCE OF VoltagesEntry
			ACCESS not-accessible
			STATUS mandatory
			::= { accessories 3 }

		
		-- 1.3.6.1.4.1.3715.100.96.3.1
		voltagesEntry OBJECT-TYPE
			SYNTAX VoltagesEntry
			ACCESS not-accessible
			STATUS mandatory
			DESCRIPTION
				"A table of measured voltages.
				First index: functionalModuleId: defines functional module containing this measured voltage
				Second index: voltageIndex: differentiates different voltage measurements (+12 V, +24 V, remote etc.)."
			INDEX { functionalModuleId, voltageIndex }
			::= { voltagesTable 1 }

		
		VoltagesEntry ::=
			SEQUENCE { 
				voltageIndex
					INTEGER,
				voltageValue
					INTEGER
			 }

		-- 1.3.6.1.4.1.3715.100.96.3.1.1
		voltageIndex OBJECT-TYPE
			SYNTAX INTEGER (1..65535)
			ACCESS read-write
			STATUS mandatory
			::= { voltagesEntry 1 }

		
		-- 1.3.6.1.4.1.3715.100.96.3.1.3
		voltageValue OBJECT-TYPE
			SYNTAX INTEGER
			ACCESS read-only
			STATUS mandatory
			DESCRIPTION
				"Measures voltage value.
				Unit 0.01 V."
			::= { voltagesEntry 3 }

		
		-- 1.3.6.1.4.1.3715.100.96.4
		universalPluginTable OBJECT-TYPE
			SYNTAX SEQUENCE OF UniversalPluginEntry
			ACCESS not-accessible
			STATUS mandatory
			DESCRIPTION
				"A table of plugins."
			::= { accessories 4 }

		
		-- 1.3.6.1.4.1.3715.100.96.4.1
		universalPluginEntry OBJECT-TYPE
			SYNTAX UniversalPluginEntry
			ACCESS not-accessible
			STATUS mandatory
			INDEX { functionalModuleId }
			::= { universalPluginTable 1 }

		
		UniversalPluginEntry ::=
			SEQUENCE { 
				universalPluginType
					INTEGER,
				universalPluginStatus
					INTEGER,
				universalPluginControl
					INTEGER
			 }

		-- 1.3.6.1.4.1.3715.100.96.4.1.1
		universalPluginType OBJECT-TYPE
			SYNTAX INTEGER
				{
				universalPluginNoPlugin(1),
				universalPluginOther(2),
				universalPluginUnknown(3),
				universalPluginTXS802(4),
				universalPluginTXS804(5),
				universalPluginTXS808(6),
				universalPluginTXE605(7),
				universalPluginTXE602(8),
				universalPluginTDA802(9),
				universalPluginTDA804(10),
				universalPluginTXS004(11),
				universalPluginTXS008(12),
				universalPluginTXS012(13),
				universalPluginTDE802(14),
				universalPluginTDE805(15),
				universalPluginTDE807(16),
				universalPluginTDE810(17),
				universalPluginTDE812(18),
				universalPluginTDE815(19),
				universalPluginTDE817(20),
				universalPluginTDE820(21),
				universalPluginTDE822(22),
				universalPluginTDE825(23),
				universalPluginTJE002(24),
				universalPluginTJE005(25),
				universalPluginTJE007(26),
				universalPluginTJE010(27),
				universalPluginTJE012(28),
				universalPluginTJE015(29),
				universalPluginTJE017(30),
				universalPluginTJE020(31),
				universalPluginTJE022(32),
				universalPluginTJE025(33),
				universalPluginTNE002(34),
				universalPluginTNE005(35),
				universalPluginTNE007(36),
				universalPluginTNE010(37),
				universalPluginTNE012(38),
				universalPluginTNE015(39),
				universalPluginTNE017(40),
				universalPluginTNE020(41),
				universalPluginTNE022(42),
				universalPluginTNE025(43),
				universalPluginTXX258(44),
				universalPluginTXX258v2(129),
				universalPluginTXS004v2(130),
				universalPluginTXS008v2(131),
				universalPluginTXS012v2(132),
				universalPluginTXS015v2(133),
				universalPluginTXX1G2v2(134),
				universalPluginTXX2C1v2(135),
				universalPluginTXX2C2v2(136),
				universalPluginTXX4C1v2(137),
				universalPluginAC630(202),
				universalPluginAC631(203)
				}
			ACCESS read-write
			STATUS mandatory
			DESCRIPTION
				"Type of plugin.
				1: no plugin, 
				2: other, 
				3: unknown, 
				4: TXS802 cable simulator, 
				5: TXS804 cable simulator, 
				6: TXS808 cable simulator, 
				7: TXE605 equaliser, 
				8: TXE602 equaliser, 
				9: TDA802 attenuator, 
				10: TDA804 attenuator,
				11: TXS004 1218 MHz cable simulator 4 dB,
				12: TXS008 1218 MHz cable simulator 8 dB,
				13: TXS012 1218 MHz cable simulator 12 dB,
				14: TDE802 862 MHz tilt 2.5 dB,
				15: TDE805 862 MHz tilt 5 dB,
				16: TDE807 862 MHz tilt 7.5 dB,
				17: TDE810 862 MHz tilt 10 dB,
				18: TDE812 862 MHz tilt 12.5 dB,
				19: TDE815 862 MHz tilt 15 dB,
				20: TDE817 862 MHz tilt 17.5 dB,
				21: TDE820 862 MHz tilt 20 dB,
				22: TDE822 862 MHz tilt 22.5 dB,
				23: TDE825 862 MHz tilt 25 dB,
				24: TJE002 1006 MHz tilt 2.5 dB,
				25: TJE005 1006 MHz tilt 5 dB,
				26: TJE007 1006 MHz tilt 7.5 dB,
				27: TJE010 1006 MHz tilt 10 dB,
				28: TJE012 1006 MHz tilt 12.5 dB,
				29: TJE015 1006 MHz tilt 15 dB,
				30: TJE017 1006 MHz tilt 17.5 dB,
				31: TJE020 1006 MHz tilt 20 dB,
				32: TJE022 1006 MHz tilt 22.5 dB,
				33: TJE025 1006 MHz tilt 25 dB,
				34: TNE002 1218 MHz tilt 2.5 dB,
				35: TNE005 1218 MHz tilt 5 dB,
				36: TNE007 1218 MHz tilt 7.5 dB,
				37: TNE010 1218 MHz tilt 10 dB,
				38: TNE012 1218 MHz tilt 12.5 dB,
				39: TNE015 1218 MHz tilt 15 dB,
				40: TNE017 1218 MHz tilt 17.5 dB,
				41: TNE020 1218 MHz tilt 20 dB,
				42: TNE022 1218 MHz tilt 22.5 dB,
				43: TNE025 1218 MHz tilt 25 dB,
				44: TXX258 258 MHz peak,
				129: TXX258v2 258 MHz peak,
				130: TXS004v2 1218 MHz cable simulator 4 dB,
				131: TXS008v2 1218 MHz cable simulator 8 dB,
				132: TXS012v2 1218 MHz cable simulator 12 dB,
				133: TXS015v2 1218 MHz cable simulator 15 dB,
				134: TXX1G2v2 1218 MHz peak
				135: TXX2C1v2 258 MHz peak and 1218 MHz peak
				136: TXX2C2v2 response correction plug
				137: TXX4C1v2 response correction plug
				202: AC630: 834 HPF (1.8 GHz)
				203: AC631 (1.8 GHz)
				"
			::= { universalPluginEntry 1 }

		
		-- 1.3.6.1.4.1.3715.100.96.4.1.2
		universalPluginStatus OBJECT-TYPE
			SYNTAX INTEGER
				{
				pluginStatusUnknown(1),
				pluginStatusNoPlugSlot(2),
				pluginStatusNotInstalled(3),
				pluginStatusInstalledAndInUse(4),
				pluginStatusInstalledButNotInUse(5)
				}
			ACCESS read-only
			STATUS mandatory
			DESCRIPTION
				"Current status of plug.
				1: Plug status unknown
				2: No plug slot available.
				3: Plug not installed (but plug slot exists).
				4: Plug is installed and in use.
				5: Plug is installed, but plug is not in use."
			::= { universalPluginEntry 2 }

		
		-- 1.3.6.1.4.1.3715.100.96.4.1.3
		universalPluginControl OBJECT-TYPE
			SYNTAX INTEGER
				{
				pluginControlUsePlugIfInstalled(1),
				pluginControlNeverUsePlug(2),
				pluginControlNA(3)
				}
			ACCESS read-write
			STATUS mandatory
			DESCRIPTION
				"Plug usage control.
				1: Use plug, if plug installed.
				2: Never use plug.
				3: pluginControlNA(3) is returned, if platform has no plug slot."
			::= { universalPluginEntry 3 }

		
		-- 1.3.6.1.4.1.3715.100.96.5
		inputOutputModuleTable OBJECT-TYPE
			SYNTAX SEQUENCE OF InputOutputModuleEntry
			ACCESS not-accessible
			STATUS mandatory
			DESCRIPTION
				"A table of automatically detected input and output modules."
			::= { accessories 5 }

		
		-- 1.3.6.1.4.1.3715.100.96.5.1
		inputOutputModuleEntry OBJECT-TYPE
			SYNTAX InputOutputModuleEntry
			ACCESS not-accessible
			STATUS mandatory
			INDEX { functionalModuleId }
			::= { inputOutputModuleTable 1 }

		
		InputOutputModuleEntry ::=
			SEQUENCE { 
				inputOutputModuleType
					INTEGER
			 }

		-- 1.3.6.1.4.1.3715.100.96.5.1.1
		inputOutputModuleType OBJECT-TYPE
			SYNTAX INTEGER
				{
				inputOutputModuleShort(1),
				inputOutputModuleAC601(2),
				inputOutputModuleAC602(3),
				inputOutputModuleAC605(4),
				inputOutputModuleAC608(5),
				inputOutputModuleAC612(6),
				inputOutputModuleAC616(7),
				inputOutputModuleOpen(15),
				inputOutputModuleReserved(16),
				inputOutputModuleUnknown(17),
				inputOutputModuleNA(18)
				}
			ACCESS read-only
			STATUS mandatory
			DESCRIPTION
				"Automatically detected 1.8 GHz input and output module type. 
				1: short, 
				2: AC601, 
				3: AC602, 
				4: AC605, 
				5: AC608, 
				6: AC612, 
				7: AC616, 
				8…14: reservedForNewTypes, 
				15: open, 
				16: reserved, 
				17: unknown; 
				18: N/A."
			::= { inputOutputModuleEntry 1 }

		
	
	END

--
-- TELESTE-FUNCTIONAL-ACCESSORIES-MIB.mib
--
