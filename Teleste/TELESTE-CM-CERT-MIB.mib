--
-- TELESTE-CM-CERT-MIB.mib
-- MIB generated by MG-SOFT Visual MIB Builder 2021 (64-bit) Version 15.00  Build 1510
-- Friday, April 08, 2022 at 16:27:55
--

-- *****************************************************************************
-- Description: Cable modem certificate update MIB for Teleste transponders
-- 
-- Revision History:
-- -----------------
-- 
-- v1 8.4.2022 Sami Halen
-- - First version
-- 
-- ****************************************************************************
-- 

	TELESTE-CM-CERT-MIB DEFINITIONS ::= BEGIN
 
		IMPORTS
			OBJECT-TYPE			
				FROM RFC-1212			
			enterprises			
				FROM RFC1155-SMI;
	
	
--
-- Node definitions
--
	
-- This MIB module only describes the settings objects valid for
-- the cable modem part of Teleste AC698x DOCSIS transponder.
		-- 1.3.6.1.4.1.8595
		hitron OBJECT IDENTIFIER ::= { enterprises 8595 }

		
		-- 1.3.6.1.4.1.8595.1
		equipment OBJECT IDENTIFIER ::= { hitron 1 }

		
		-- 1.3.6.1.4.1.8595.1.400
		cableModem OBJECT IDENTIFIER ::= { equipment 400 }

		
		-- 1.3.6.1.4.1.8595.1.400.8
		cmCertificateUpdate OBJECT IDENTIFIER ::= { cableModem 8 }

		
		-- 1.3.6.1.4.1.8595.1.400.8.1
		cmCertUpdateFilepath OBJECT-TYPE
			SYNTAX OCTET STRING
			ACCESS read-write
			STATUS mandatory
			DESCRIPTION
				"The file path for CM certificates upgrade. The final full filename is 
				the path + CM_MAC_Address.enc. If the value for this OID is NULL, then 
				the default value AC698xNewCertificate is used.
				For example: if the value for OID is cm/certificates and CM MAC address
				is 009050abcdef, then the full filename is cm/certificates/009050abcdef.enc"
			::= { cmCertificateUpdate 1 }

		
		-- 1.3.6.1.4.1.8595.1.400.8.3
		cmCertUpdateServer OBJECT-TYPE
			SYNTAX OCTET STRING (SIZE (0..15))
			ACCESS read-write
			STATUS mandatory
			DESCRIPTION
				"The IPv4 address of the TFTP server used for CM certificates upgrade.
				If the value for this OID is NULL, then the config file TFTP server address is used."
			::= { cmCertificateUpdate 3 }

		
		-- 1.3.6.1.4.1.8595.1.400.8.4
		cmCertUpdateTrigger OBJECT-TYPE
			SYNTAX INTEGER
			ACCESS read-write
			STATUS mandatory
			DESCRIPTION
				"When set it to true, triggers the certificate update feature."
			::= { cmCertificateUpdate 4 }

		
		-- 1.3.6.1.4.1.8595.1.400.8.5
		cmCertUpdateVersion OBJECT-TYPE
			SYNTAX INTEGER
			ACCESS read-only
			STATUS mandatory
			DESCRIPTION
				"Shows current CM certificate version.
				2022: old certificate, 2031: new certificate"
			::= { cmCertificateUpdate 5 }

		
	
	END

--
-- TELESTE-CM-CERT-MIB.mib
--
