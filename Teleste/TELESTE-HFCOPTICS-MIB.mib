--
-- TELESTE-HFCOPTICS-MIB.mib
-- MIB generated by MG-SOFT Visual MIB Builder 2021 (64-bit) Version 15.00  Build 1510
-- Thursday, June 03, 2021 at 16:00:16
--

-- *****************************************************************************
-- Copyright (c) 2004-2014 by:
-- 
-- Teleste Corporation
-- Telestenkatu 1
-- FI-20660 Littoinen, Finland
-- tel. +358 2 2605 611
-- url: http://www.teleste.com
-- 
-- Description: Objects for HFC optical modules/functions. This MIB
--              only contains objects not available in the HMS-HE-MIBs.
-- 
-- 
-- Revision History:
-- -----------------
-- v13 3.6.2021 Sami Kuusisto
-- - Added new enumeration (saturated(4)) to optTxGainControlStatus.
-- 
-- v12 20.3.2019 Sami Kuusisto and Rainer Salminen.
-- - Removed optRxNodesCommunicating and optRxNodesStored.
-- 
-- v11 18.3.2019 Sami Kuusisto and Rainer Salminen
-- - Added optRxNodesCommunicating and optRxNodesStored. Updated optRxDataCarrierStatus description. Changed optRxNodeStatus.
-- 
-- v10 15.3.2019 Sami Kuusisto
-- - Added optRxNodeLastResponse and optRxNodeStatus.
-- 
-- v9 28.2.2018 Sami Kuusisto 
-- - Added optTxApcStatus and optTxApcMeasuredOffset.
-- 
-- v8 29.11.2017 Sami Kuusisto
-- - Added carrierCalibrating(4) to optRxDataCarrierStatus.
-- 
-- v7 10.6.2016 Sami Halen
-- - Added value 4 to optTxLaserPowerControlStatus
-- 
-- v6 11.11.2014 Sami Halen
-- - Added optRxNodeLidStatus to optRxNodeMonitoringTable
-- 
-- v5 9.10.2014 Sami Halen
-- - Changed optRxBerStatus to use ValueStatus
-- - Added optRxBer to optRxModuleTable
-- 
-- v4 5.8.2014 Sami Halen
-- - Changed analog alarm status objects to use ValueStatus from TELESTE-ROOT-MIB
-- - Completely rewrote optRxNodeMonitoringTable contents
-- - Added value 3 to optRxDataCarrierStatus
-- 
-- v3 30.7.2014 Sami Halen
-- - Added values 4 and 5 to optRxGainControlStatus
-- 
-- v2 26.6.2014 Matti Susi
-- - Added digital return RX objects
-- 
-- v1 21.12.2006 Matti Susi
-- - First official release
-- 
-- ****************************************************************************
-- 

	TELESTE-HFCOPTICS-MIB DEFINITIONS ::= BEGIN
 
		IMPORTS
			OBJECT-TYPE			
				FROM RFC-1212			
			mib-2			
				FROM SNMPv2-SMI			
			moduleId			
				FROM TELESTE-COMMON-MIB			
			functional, ValueStatus			
				FROM TELESTE-ROOT-MIB;
	
	
	
--
-- Node definitions
--
	
-- Optical transmitter objects
		-- 1.3.6.1.4.1.3715.100.11
		opticalTransmitter OBJECT IDENTIFIER ::= { functional 11 }

		
		-- 1.3.6.1.4.1.3715.100.11.1
		optTxTable OBJECT-TYPE
			SYNTAX SEQUENCE OF OptTxEntry
			ACCESS not-accessible
			STATUS mandatory
			::= { opticalTransmitter 1 }

		
		-- 1.3.6.1.4.1.3715.100.11.1.1
		optTxEntry OBJECT-TYPE
			SYNTAX OptTxEntry
			ACCESS not-accessible
			STATUS mandatory
			INDEX { moduleId }
			::= { optTxTable 1 }

		
		OptTxEntry ::=
			SEQUENCE { 
				optTxSlope
					INTEGER,
				optTxRFLevelTarget
					INTEGER,
				optTxRFLevelTargetCW
					INTEGER,
				optTxInputRFPowerCW
					INTEGER,
				optTxLaserPowerOffset
					INTEGER,
				optTxLaserPowerTarget
					INTEGER,
				optTxLaserPowerControlStatus
					INTEGER,
				optTxLaserTempOffset
					INTEGER,
				optTxLaserTempControlStatus
					INTEGER,
				optTxOmi
					INTEGER,
				optTxRFAmpControl
					INTEGER,
				optTxNrOfChannels
					INTEGER,
				optTxAlscStatus
					INTEGER,
				optTxGainControlStatus
					INTEGER,
				optTxInputRfPowerStatus
					ValueStatus,
				optTxLaserTecCurrentStatus
					ValueStatus,
				optTxLaserTempStatus
					ValueStatus,
				optTxLaserPowerStatus
					ValueStatus,
				optTxApcStatus
					INTEGER,
				optTxApcMeasuredOffset
					INTEGER
			 }

		-- 1.3.6.1.4.1.3715.100.11.1.1.1
		optTxSlope OBJECT-TYPE
			SYNTAX INTEGER
			ACCESS read-write
			STATUS mandatory
			DESCRIPTION
				"Optical transmitter input slope control value. Unit 0.1 dB."
			::= { optTxEntry 1 }

		
		-- 1.3.6.1.4.1.3715.100.11.1.1.2
		optTxRFLevelTarget OBJECT-TYPE
			SYNTAX INTEGER
			ACCESS read-write
			STATUS mandatory
			DESCRIPTION
				"Laser drive level target. Unit 0.01 dBuV."
			::= { optTxEntry 2 }

		
		-- 1.3.6.1.4.1.3715.100.11.1.1.3
		optTxRFLevelTargetCW OBJECT-TYPE
			SYNTAX INTEGER
			ACCESS read-write
			STATUS mandatory
			DESCRIPTION
				"Laser drive level target for CW signals. Unit 0.01 dBuV."
			::= { optTxEntry 3 }

		
		-- 1.3.6.1.4.1.3715.100.11.1.1.4
		optTxInputRFPowerCW OBJECT-TYPE
			SYNTAX INTEGER
			ACCESS read-write
			STATUS mandatory
			DESCRIPTION
				"Input signal power level for CW signals. Unit 0.01 dBuV."
			::= { optTxEntry 4 }

		
		-- 1.3.6.1.4.1.3715.100.11.1.1.5
		optTxLaserPowerOffset OBJECT-TYPE
			SYNTAX INTEGER
			ACCESS read-write
			STATUS mandatory
			DESCRIPTION
				"Laser power offset. Unit 0.01 dBm."
			::= { optTxEntry 5 }

		
		-- 1.3.6.1.4.1.3715.100.11.1.1.6
		optTxLaserPowerTarget OBJECT-TYPE
			SYNTAX INTEGER
			ACCESS read-write
			STATUS mandatory
			DESCRIPTION
				"Laser power target level. Unit 0.01 dBm."
			::= { optTxEntry 6 }

		
		-- 1.3.6.1.4.1.3715.100.11.1.1.7
		optTxLaserPowerControlStatus OBJECT-TYPE
			SYNTAX INTEGER
				{
				normal(1),
				minimum(2),
				maximum(3),
				turnedOff(4)
				}
			ACCESS read-only
			STATUS mandatory
			DESCRIPTION
				"Laser power control circuit status:
				1 = normal
				2 = minimum
				3 = maximum
				4 = turned off"
			::= { optTxEntry 7 }

		
		-- 1.3.6.1.4.1.3715.100.11.1.1.8
		optTxLaserTempOffset OBJECT-TYPE
			SYNTAX INTEGER
			ACCESS read-write
			STATUS mandatory
			DESCRIPTION
				"Laser temperature offset. Unit 0.01 degrees C."
			::= { optTxEntry 8 }

		
		-- 1.3.6.1.4.1.3715.100.11.1.1.9
		optTxLaserTempControlStatus OBJECT-TYPE
			SYNTAX INTEGER
				{
				normal(1),
				minimum(2),
				maximum(3)
				}
			ACCESS read-only
			STATUS mandatory
			DESCRIPTION
				"Laser temperature control circuit status:
				1 = normal
				2 = minimum
				3 = maximum
				"
			::= { optTxEntry 9 }

		
		-- 1.3.6.1.4.1.3715.100.11.1.1.10
		optTxOmi OBJECT-TYPE
			SYNTAX INTEGER
			ACCESS read-only
			STATUS mandatory
			DESCRIPTION
				"OMI per channel. Unit 1 %."
			::= { optTxEntry 10 }

		
		-- 1.3.6.1.4.1.3715.100.11.1.1.11
		optTxRFAmpControl OBJECT-TYPE
			SYNTAX INTEGER
				{
				off(1),
				on(2)
				}
			ACCESS read-write
			STATUS mandatory
			DESCRIPTION
				"Transmitter RF amplifier control:
				1 = amplifier OFF
				2 = amplifier ON"
			::= { optTxEntry 11 }

		
		-- 1.3.6.1.4.1.3715.100.11.1.1.12
		optTxNrOfChannels OBJECT-TYPE
			SYNTAX INTEGER (1..200)
			ACCESS read-write
			STATUS mandatory
			DESCRIPTION
				"Number of channels in use. This value is used to calculate
				the OMI per channel value."
			::= { optTxEntry 12 }

		
		-- 1.3.6.1.4.1.3715.100.11.1.1.13
		optTxAlscStatus OBJECT-TYPE
			SYNTAX INTEGER
			ACCESS read-only
			STATUS mandatory
			DESCRIPTION
				"Automatic level control status:
				1 = manual mode, ALC disabled
				2 = factory
				3 = normal
				4 = limit"
			::= { optTxEntry 13 }

		
		-- 1.3.6.1.4.1.3715.100.11.1.1.14
		optTxGainControlStatus OBJECT-TYPE
			SYNTAX INTEGER
				{
				normal(1),
				minimum(2),
				maximum(3),
				saturated(4)
				}
			ACCESS read-only
			STATUS mandatory
			DESCRIPTION
				"Gain control attenuator status:
				1 = normal
				2 = minimum attenuation
				3 = maximum attenuation
				4 = saturated
				"
			::= { optTxEntry 14 }

		
		-- 1.3.6.1.4.1.3715.100.11.1.1.15
		optTxInputRfPowerStatus OBJECT-TYPE
			SYNTAX ValueStatus
			ACCESS read-only
			STATUS mandatory
			DESCRIPTION
				"Input RF power status:
				1 = normal
				2 = HiHi
				3 = Hi
				4 = Lo
				5 = LoLo
				"
			::= { optTxEntry 15 }

		
		-- 1.3.6.1.4.1.3715.100.11.1.1.16
		optTxLaserTecCurrentStatus OBJECT-TYPE
			SYNTAX ValueStatus
			ACCESS read-only
			STATUS mandatory
			DESCRIPTION
				"Laser TEC current status:
				1 = normal
				2 = HiHi
				3 = Hi
				4 = Lo
				5 = LoLo
				"
			::= { optTxEntry 16 }

		
		-- 1.3.6.1.4.1.3715.100.11.1.1.17
		optTxLaserTempStatus OBJECT-TYPE
			SYNTAX ValueStatus
			ACCESS read-only
			STATUS mandatory
			DESCRIPTION
				"Laser temperature status:
				1 = normal
				2 = HIHI
				3 = Hi
				4 = Lo
				5 = LOLO"
			::= { optTxEntry 17 }

		
		-- 1.3.6.1.4.1.3715.100.11.1.1.18
		optTxLaserPowerStatus OBJECT-TYPE
			SYNTAX ValueStatus
			ACCESS read-only
			STATUS mandatory
			DESCRIPTION
				"Laser power status:
				1 = normal
				2 = HIHI
				3 = Hi
				4 = Lo
				5 = LOLO"
			::= { optTxEntry 18 }

		
		-- 1.3.6.1.4.1.3715.100.11.1.1.19
		optTxApcStatus OBJECT-TYPE
			SYNTAX INTEGER
				{
				apcStatusNormal(1),
				apcStatusHigh(2),
				apcStatusLow(3),
				apcStatusNearLimit(4)
				}
			ACCESS read-only
			STATUS mandatory
			DESCRIPTION
				"APC status
				1: Normal
				2: High
				3: Low
				4: Near limit"
			::= { optTxEntry 19 }

		
		-- 1.3.6.1.4.1.3715.100.11.1.1.20
		optTxApcMeasuredOffset OBJECT-TYPE
			SYNTAX INTEGER
			ACCESS read-only
			STATUS mandatory
			DESCRIPTION
				"Measured APC offset. Unit 0,01 dB."
			::= { optTxEntry 20 }

		
		-- 1.3.6.1.4.1.3715.100.11.2
		optTxPilotGenTable OBJECT-TYPE
			SYNTAX SEQUENCE OF OptTxPilotGenEntry
			ACCESS not-accessible
			STATUS mandatory
			::= { opticalTransmitter 2 }

		
		-- 1.3.6.1.4.1.3715.100.11.2.1
		optTxPilotGenEntry OBJECT-TYPE
			SYNTAX OptTxPilotGenEntry
			ACCESS not-accessible
			STATUS mandatory
			INDEX { moduleId }
			::= { optTxPilotGenTable 1 }

		
		OptTxPilotGenEntry ::=
			SEQUENCE { 
				pilotGenControl
					INTEGER,
				pilotGenALCControl
					INTEGER,
				pilotGenALCStatus
					INTEGER,
				pilotGenPadControl
					INTEGER,
				pilotGenExcessPadControl
					INTEGER,
				pilotGenLPFilterControl
					INTEGER,
				pilotGenPadStatus
					INTEGER,
				pilotGenFrequency
					INTEGER,
				pilotGenLevel
					INTEGER,
				pilotGenPLLStatus
					INTEGER
			 }

		-- 1.3.6.1.4.1.3715.100.11.2.1.1
		pilotGenControl OBJECT-TYPE
			SYNTAX INTEGER
				{
				off(1),
				on(2)
				}
			ACCESS read-write
			STATUS mandatory
			DESCRIPTION
				"Pilot generator control:
				1 = generator OFF
				2 = generator ON"
			::= { optTxPilotGenEntry 1 }

		
		-- 1.3.6.1.4.1.3715.100.11.2.1.2
		pilotGenALCControl OBJECT-TYPE
			SYNTAX INTEGER
				{
				off(1),
				on(2)
				}
			ACCESS read-write
			STATUS mandatory
			DESCRIPTION
				"Pilot generator automatic level circuit control:
				1 = ALC OFF
				2 = ALC ON"
			::= { optTxPilotGenEntry 2 }

		
		-- 1.3.6.1.4.1.3715.100.11.2.1.3
		pilotGenALCStatus OBJECT-TYPE
			SYNTAX INTEGER
				{
				manual(1),
				factory(2),
				normal(3),
				limit(4)
				}
			ACCESS read-only
			STATUS mandatory
			DESCRIPTION
				"Pilot generator automatic level circuit status:
				1 = manual mode, ALC disabled
				2 = factory
				3 = normal
				4 = limit"
			::= { optTxPilotGenEntry 3 }

		
		-- 1.3.6.1.4.1.3715.100.11.2.1.4
		pilotGenPadControl OBJECT-TYPE
			SYNTAX INTEGER
			ACCESS read-write
			STATUS mandatory
			DESCRIPTION
				"Pilot generator attenuator value. Unit 0.1 dB."
			::= { optTxPilotGenEntry 4 }

		
		-- 1.3.6.1.4.1.3715.100.11.2.1.6
		pilotGenExcessPadControl OBJECT-TYPE
			SYNTAX INTEGER
				{
				off(1),
				on(2)
				}
			ACCESS read-write
			STATUS mandatory
			DESCRIPTION
				"Pilot generator extra attenuator control:
				1 = attenuator OFF
				2 = attenuator ON"
			::= { optTxPilotGenEntry 6 }

		
		-- 1.3.6.1.4.1.3715.100.11.2.1.7
		pilotGenLPFilterControl OBJECT-TYPE
			SYNTAX INTEGER
				{
				off(1),
				on(2)
				}
			ACCESS read-write
			STATUS mandatory
			DESCRIPTION
				"Pilot generator low pass filter control:
				1 = low pass filter OFF
				2 = low pass filter ON"
			::= { optTxPilotGenEntry 7 }

		
		-- 1.3.6.1.4.1.3715.100.11.2.1.8
		pilotGenPadStatus OBJECT-TYPE
			SYNTAX INTEGER
				{
				normal(1),
				minimum(2),
				maximum(3)
				}
			ACCESS read-only
			STATUS mandatory
			DESCRIPTION
				"Pilot attenuator status:
				1 = normal
				2 = minimum attenuation
				3 = maximum attenuation
				
				With manual gain control the value should always be 1."
			::= { optTxPilotGenEntry 8 }

		
		-- 1.3.6.1.4.1.3715.100.11.2.1.9
		pilotGenFrequency OBJECT-TYPE
			SYNTAX INTEGER
			ACCESS read-write
			STATUS mandatory
			DESCRIPTION
				"Pilot signal frequency. Unit 1 KHz."
			::= { optTxPilotGenEntry 9 }

		
		-- 1.3.6.1.4.1.3715.100.11.2.1.10
		pilotGenLevel OBJECT-TYPE
			SYNTAX INTEGER
			ACCESS read-only
			STATUS mandatory
			DESCRIPTION
				"Pilot signal level, Unit 0.01 dBuV."
			::= { optTxPilotGenEntry 10 }

		
		-- 1.3.6.1.4.1.3715.100.11.2.1.11
		pilotGenPLLStatus OBJECT-TYPE
			SYNTAX INTEGER
				{
				locked(1),
				unlocked(2)
				}
			ACCESS read-only
			STATUS mandatory
			DESCRIPTION
				"Pilot oscillator PLL status:
				1 = locked
				2 = unlocked"
			::= { optTxPilotGenEntry 11 }

		
		-- 1.3.6.1.4.1.3715.100.11.3
		optTxDtmfTxTable OBJECT-TYPE
			SYNTAX SEQUENCE OF OptTxDtmfTxEntry
			ACCESS not-accessible
			STATUS mandatory
			::= { opticalTransmitter 3 }

		
		-- 1.3.6.1.4.1.3715.100.11.3.1
		optTxDtmfTxEntry OBJECT-TYPE
			SYNTAX OptTxDtmfTxEntry
			ACCESS not-accessible
			STATUS mandatory
			INDEX { moduleId }
			::= { optTxDtmfTxTable 1 }

		
		OptTxDtmfTxEntry ::=
			SEQUENCE { 
				dtmfToneControl
					INTEGER,
				dtmfAControl
					INTEGER,
				dtmfBControl
					INTEGER,
				dtmfCControl
					INTEGER,
				dtmfDControl
					INTEGER
			 }

		-- 1.3.6.1.4.1.3715.100.11.3.1.1
		dtmfToneControl OBJECT-TYPE
			SYNTAX INTEGER
				{
				off(1),
				on(2)
				}
			ACCESS read-write
			STATUS mandatory
			DESCRIPTION
				"DTMF tone control:
				1 = tones OFF
				2 = tones ON"
			::= { optTxDtmfTxEntry 1 }

		
		-- 1.3.6.1.4.1.3715.100.11.3.1.2
		dtmfAControl OBJECT-TYPE
			SYNTAX INTEGER
				{
				off(1),
				on(2)
				}
			ACCESS read-write
			STATUS mandatory
			DESCRIPTION
				"DTMF signal A control:
				1 = signal OFF
				2 = signal ON"
			::= { optTxDtmfTxEntry 2 }

		
		-- 1.3.6.1.4.1.3715.100.11.3.1.3
		dtmfBControl OBJECT-TYPE
			SYNTAX INTEGER
				{
				off(1),
				on(2)
				}
			ACCESS read-write
			STATUS mandatory
			DESCRIPTION
				"DTMF signal B control:
				1 = signal OFF
				2 = signal ON"
			::= { optTxDtmfTxEntry 3 }

		
		-- 1.3.6.1.4.1.3715.100.11.3.1.4
		dtmfCControl OBJECT-TYPE
			SYNTAX INTEGER
				{
				off(1),
				on(2)
				}
			ACCESS read-write
			STATUS mandatory
			DESCRIPTION
				"DTMF signal C control:
				1 = signal OFF
				2 = signal ON"
			::= { optTxDtmfTxEntry 4 }

		
		-- 1.3.6.1.4.1.3715.100.11.3.1.5
		dtmfDControl OBJECT-TYPE
			SYNTAX INTEGER
				{
				off(1),
				on(2)
				}
			ACCESS read-write
			STATUS mandatory
			DESCRIPTION
				"DTMF signal D control:
				1 = signal OFF
				2 = signal ON"
			::= { optTxDtmfTxEntry 5 }

		
-- Optical receiver objects
		-- 1.3.6.1.4.1.3715.100.12
		opticalReceiver OBJECT IDENTIFIER ::= { functional 12 }

		
		-- 1.3.6.1.4.1.3715.100.12.1
		optRxTable OBJECT-TYPE
			SYNTAX SEQUENCE OF OptRxEntry
			ACCESS not-accessible
			STATUS mandatory
			DESCRIPTION
				"A table of objects common to all submodules innside the physical 
				receiver module."
			::= { opticalReceiver 1 }

		
		-- 1.3.6.1.4.1.3715.100.12.1.1
		optRxEntry OBJECT-TYPE
			SYNTAX OptRxEntry
			ACCESS not-accessible
			STATUS mandatory
			INDEX { moduleId }
			::= { optRxTable 1 }

		
		OptRxEntry ::=
			SEQUENCE { 
				optRxRoutingControl
					INTEGER
			 }

		-- 1.3.6.1.4.1.3715.100.12.1.1.1
		optRxRoutingControl OBJECT-TYPE
			SYNTAX INTEGER
			ACCESS read-write
			STATUS mandatory
			DESCRIPTION
				"Dual receiver routing control. Bit based coding.
				"
			::= { optRxEntry 1 }

		
		-- 1.3.6.1.4.1.3715.100.12.2
		optRxModuleTable OBJECT-TYPE
			SYNTAX SEQUENCE OF OptRxModuleEntry
			ACCESS not-accessible
			STATUS mandatory
			DESCRIPTION
				"A table of objects related to individual receiver modules inside the
				physical receiver module."
			::= { opticalReceiver 2 }

		
		-- 1.3.6.1.4.1.3715.100.12.2.1
		optRxModuleEntry OBJECT-TYPE
			SYNTAX OptRxModuleEntry
			ACCESS not-accessible
			STATUS mandatory
			INDEX { moduleId, optRxId }
			::= { optRxModuleTable 1 }

		
		OptRxModuleEntry ::=
			SEQUENCE { 
				optRxId
					INTEGER,
				optRxNominalInputPower
					INTEGER,
				optRxALCPilotTarget
					INTEGER,
				optRxALCStatus
					INTEGER,
				optRxGainControlStatus
					INTEGER,
				optRxControl
					INTEGER,
				optRxAmpControl
					INTEGER,
				optRxSetManualGain
					INTEGER,
				optRxALCControl
					INTEGER,
				optRxSlope
					INTEGER,
				optRxInputPowerStatus
					ValueStatus,
				optRxOutputLevelStatus
					ValueStatus,
				optRxBerStatus
					ValueStatus,
				optRxDataCarrierStatus
					INTEGER,
				optRxBer
					INTEGER
			 }

		-- 1.3.6.1.4.1.3715.100.12.2.1.1
		optRxId OBJECT-TYPE
			SYNTAX INTEGER (1..16)
			ACCESS read-only
			STATUS mandatory
			DESCRIPTION
				"Second index to the table. If the module contains only one 
				functional entity, optRxId 1 is used. With more functional 
				entities, each of them is numbered with a unique opRxId (eg.
				multiple optical receivers in a module).
				
				The optRxIdshould should be identical to the function 
				entity indexes used in the HMS-HE-MIBs (eg.heOpRxInputIndex, 
				heOpRxOutputIndex etc.).
				"
			::= { optRxModuleEntry 1 }

		
		-- 1.3.6.1.4.1.3715.100.12.2.1.2
		optRxNominalInputPower OBJECT-TYPE
			SYNTAX INTEGER
			ACCESS read-write
			STATUS mandatory
			DESCRIPTION
				"Nominal input power value. Unit 0.01 dBm."
			::= { optRxModuleEntry 2 }

		
		-- 1.3.6.1.4.1.3715.100.12.2.1.3
		optRxALCPilotTarget OBJECT-TYPE
			SYNTAX INTEGER
			ACCESS read-write
			STATUS mandatory
			DESCRIPTION
				"Target pilot level for automatic level control.
				Unit 0.01 dBuV."
			::= { optRxModuleEntry 3 }

		
		-- 1.3.6.1.4.1.3715.100.12.2.1.4
		optRxALCStatus OBJECT-TYPE
			SYNTAX INTEGER
				{
				manual(1),
				factory(2),
				normal(3)
				}
			ACCESS read-only
			STATUS mandatory
			DESCRIPTION
				"ALC status:
				1 = manual
				2 = factory set
				3 = normal
				"
			::= { optRxModuleEntry 4 }

		
		-- 1.3.6.1.4.1.3715.100.12.2.1.5
		optRxGainControlStatus OBJECT-TYPE
			SYNTAX INTEGER
				{
				normal(1),
				minimum(2),
				maximum(3),
				nearLimit(4),
				atLimit(5)
				}
			ACCESS read-only
			STATUS mandatory
			DESCRIPTION
				"Gain control pad (attenuator) status:
				1 = normal
				2 = minimum attenuation
				3 = maximum attenuation
				4 = close to minimum/maximum, but still in operating range
				5 = at minimum/maximum
				
				Typically devices implement either values (1,2,3) or values (1,4,5)
				With manual gain control the value should always be 1."
			::= { optRxModuleEntry 5 }

		
		-- 1.3.6.1.4.1.3715.100.12.2.1.6
		optRxControl OBJECT-TYPE
			SYNTAX INTEGER
				{
				on(1),
				off(2)
				}
			ACCESS read-write
			STATUS mandatory
			DESCRIPTION
				"Optical receiver control:
				1 = receiver ON
				2 = receiver OFF"
			::= { optRxModuleEntry 6 }

		
		-- 1.3.6.1.4.1.3715.100.12.2.1.7
		optRxAmpControl OBJECT-TYPE
			SYNTAX INTEGER
				{
				on(1),
				off(2)
				}
			ACCESS read-write
			STATUS mandatory
			DESCRIPTION
				"Receiver RF amplifier control:
				1 = amplifier ON
				2 = amplifier OFF"
			::= { optRxModuleEntry 7 }

		
		-- 1.3.6.1.4.1.3715.100.12.2.1.8
		optRxSetManualGain OBJECT-TYPE
			SYNTAX INTEGER { set(1) }
			ACCESS read-write
			STATUS mandatory
			DESCRIPTION
				"Set current gain value as the manual control value.
				Reading this object always returns value 1."
			::= { optRxModuleEntry 8 }

		
		-- 1.3.6.1.4.1.3715.100.12.2.1.9
		optRxALCControl OBJECT-TYPE
			SYNTAX INTEGER
				{
				on(1),
				off(2)
				}
			ACCESS read-write
			STATUS mandatory
			DESCRIPTION
				"ALC control:
				1 = ALC ON
				2 = ALC OFF"
			::= { optRxModuleEntry 9 }

		
		-- 1.3.6.1.4.1.3715.100.12.2.1.10
		optRxSlope OBJECT-TYPE
			SYNTAX INTEGER
			ACCESS read-write
			STATUS mandatory
			DESCRIPTION
				"Receiver slope control value. Unit 0.01 dB.
				"
			::= { optRxModuleEntry 10 }

		
		-- 1.3.6.1.4.1.3715.100.12.2.1.11
		optRxInputPowerStatus OBJECT-TYPE
			SYNTAX ValueStatus
			ACCESS read-only
			STATUS mandatory
			DESCRIPTION
				"Optical input power status:
				1 = normal
				2 = HiHi
				3 = Hi
				4 = Lo
				5 = LoLo
				"
			::= { optRxModuleEntry 11 }

		
		-- 1.3.6.1.4.1.3715.100.12.2.1.12
		optRxOutputLevelStatus OBJECT-TYPE
			SYNTAX ValueStatus
			ACCESS read-only
			STATUS mandatory
			DESCRIPTION
				"Output RF level status:
				1 = normal
				2 = HiHi
				3 = Hi
				4 = Lo
				5 = LoLo
				"
			::= { optRxModuleEntry 12 }

		
		-- 1.3.6.1.4.1.3715.100.12.2.1.13
		optRxBerStatus OBJECT-TYPE
			SYNTAX ValueStatus
			ACCESS read-only
			STATUS mandatory
			DESCRIPTION
				"Bit error rate status:
				1 = normal
				2 = HiHi
				3 = Hi
				4 = Lo
				5 = LoLo"
			::= { optRxModuleEntry 13 }

		
		-- 1.3.6.1.4.1.3715.100.12.2.1.14
		optRxDataCarrierStatus OBJECT-TYPE
			SYNTAX INTEGER
				{
				carrierOk(1),
				carrierMissing(2),
				carrierCorrupted(3),
				carrierCalibrating(4)
				}
			ACCESS read-only
			STATUS mandatory
			DESCRIPTION
				"Data carrier status, values:
				
				When single node mode
				carrierOk(1) = data carrier is detected
				carrierMissing(2) = data carrier is not detected
				carrierCorrupted(3) = data carrier detected but corrupted
				carrierCalibrating(4) = Receiver is adjusting to input signal, RF output may be affected.
				
				When multi node mode
				1: Communicating nodes and stored nodes list matches.
				2: Communicating nodes and stored nodes list does not match."
			::= { optRxModuleEntry 14 }

		
		-- 1.3.6.1.4.1.3715.100.12.2.1.15
		optRxBer OBJECT-TYPE
			SYNTAX INTEGER
			ACCESS read-only
			STATUS mandatory
			DESCRIPTION
				"Measured BER value exponent*100.
				BER=10^(optRxBer/100)"
			::= { optRxModuleEntry 15 }

		
		-- 1.3.6.1.4.1.3715.100.12.3
		optRxPilotReceiverTable OBJECT-TYPE
			SYNTAX SEQUENCE OF OptRxPilotReceiverEntry
			ACCESS not-accessible
			STATUS mandatory
			::= { opticalReceiver 3 }

		
		-- 1.3.6.1.4.1.3715.100.12.3.1
		optRxPilotReceiverEntry OBJECT-TYPE
			SYNTAX OptRxPilotReceiverEntry
			ACCESS not-accessible
			STATUS mandatory
			INDEX { moduleId, optRxId }
			::= { optRxPilotReceiverTable 1 }

		
		OptRxPilotReceiverEntry ::=
			SEQUENCE { 
				pilotReceiverFrequency
					INTEGER,
				pilotReceiverPLLStatus
					INTEGER,
				pilotReceiverPilotStatus
					INTEGER
			 }

		-- 1.3.6.1.4.1.3715.100.12.3.1.1
		pilotReceiverFrequency OBJECT-TYPE
			SYNTAX INTEGER
			ACCESS read-write
			STATUS mandatory
			DESCRIPTION
				"Pilot signal frequency. Unit 1 KHz."
			::= { optRxPilotReceiverEntry 1 }

		
		-- 1.3.6.1.4.1.3715.100.12.3.1.2
		pilotReceiverPLLStatus OBJECT-TYPE
			SYNTAX INTEGER
				{
				locked(1),
				unlocked(2)
				}
			ACCESS read-only
			STATUS mandatory
			DESCRIPTION
				"Pilot oscillator PLL status:
				1 = locked
				2 = unlocked"
			::= { optRxPilotReceiverEntry 2 }

		
		-- 1.3.6.1.4.1.3715.100.12.3.1.3
		pilotReceiverPilotStatus OBJECT-TYPE
			SYNTAX INTEGER
				{
				on(1),
				off(2)
				}
			ACCESS read-only
			STATUS mandatory
			DESCRIPTION
				"Pilot status:
				1 = pilot ON
				2 = pilot OFF"
			::= { optRxPilotReceiverEntry 3 }

		
		-- 1.3.6.1.4.1.3715.100.12.4
		optRxDtmfRxTable OBJECT-TYPE
			SYNTAX SEQUENCE OF OptRxDtmfRxEntry
			ACCESS not-accessible
			STATUS mandatory
			::= { opticalReceiver 4 }

		
		-- 1.3.6.1.4.1.3715.100.12.4.1
		optRxDtmfRxEntry OBJECT-TYPE
			SYNTAX OptRxDtmfRxEntry
			ACCESS not-accessible
			STATUS mandatory
			INDEX { moduleId, optRxId }
			::= { optRxDtmfRxTable 1 }

		
		OptRxDtmfRxEntry ::=
			SEQUENCE { 
				dtmfToneStatus
					INTEGER,
				dtmfAStatus
					INTEGER,
				dtmfBStatus
					INTEGER,
				dtmfCStatus
					INTEGER,
				dtmfDStatus
					INTEGER
			 }

		-- 1.3.6.1.4.1.3715.100.12.4.1.1
		dtmfToneStatus OBJECT-TYPE
			SYNTAX INTEGER
				{
				off(1),
				on(2)
				}
			ACCESS read-only
			STATUS mandatory
			DESCRIPTION
				"DTMF tone status:
				1 = tones OFF
				2 = tones ON"
			::= { optRxDtmfRxEntry 1 }

		
		-- 1.3.6.1.4.1.3715.100.12.4.1.2
		dtmfAStatus OBJECT-TYPE
			SYNTAX INTEGER
				{
				off(1),
				on(2)
				}
			ACCESS read-only
			STATUS mandatory
			DESCRIPTION
				"DTMF signal A status:
				1 = signal OFF
				2 = signal ON"
			::= { optRxDtmfRxEntry 2 }

		
		-- 1.3.6.1.4.1.3715.100.12.4.1.3
		dtmfBStatus OBJECT-TYPE
			SYNTAX INTEGER
				{
				off(1),
				on(2)
				}
			ACCESS read-only
			STATUS mandatory
			DESCRIPTION
				"DTMF signal B status:
				1 = signal OFF
				2 = signal ON"
			::= { optRxDtmfRxEntry 3 }

		
		-- 1.3.6.1.4.1.3715.100.12.4.1.4
		dtmfCStatus OBJECT-TYPE
			SYNTAX INTEGER
				{
				off(1),
				on(2)
				}
			ACCESS read-only
			STATUS mandatory
			DESCRIPTION
				"DTMF signal C status:
				1 = signal OFF
				2 = signal ON"
			::= { optRxDtmfRxEntry 4 }

		
		-- 1.3.6.1.4.1.3715.100.12.4.1.5
		dtmfDStatus OBJECT-TYPE
			SYNTAX INTEGER
				{
				off(1),
				on(2)
				}
			ACCESS read-only
			STATUS mandatory
			DESCRIPTION
				"DTMF signal D status:
				1 = signal OFF
				2 = signal ON"
			::= { optRxDtmfRxEntry 5 }

		
		-- 1.3.6.1.4.1.3715.100.12.10
		optRxNodeMonitoringTable OBJECT-TYPE
			SYNTAX SEQUENCE OF OptRxNodeMonitoringEntry
			ACCESS not-accessible
			STATUS mandatory
			DESCRIPTION
				"A table of objects related to monitoring data sent 
				by optical node(s) via inband data link."
			::= { opticalReceiver 10 }

		
		-- 1.3.6.1.4.1.3715.100.12.10.1
		optRxNodeMonitoringEntry OBJECT-TYPE
			SYNTAX OptRxNodeMonitoringEntry
			ACCESS not-accessible
			STATUS mandatory
			INDEX { moduleId, optRxId, optRxNodeId }
			::= { optRxNodeMonitoringTable 1 }

		
		OptRxNodeMonitoringEntry ::=
			SEQUENCE { 
				optRxNodeId
					INTEGER,
				optRxNodeCpuStatus
					INTEGER,
				optRxNodeTempStatus
					ValueStatus,
				optRxNodeLaserCurrentStatus
					ValueStatus,
				optRxNodeNoiseLevelStatus
					ValueStatus,
				optRxNodeRfOutput1Status
					ValueStatus,
				optRxNodeRfOutput2Status
					ValueStatus,
				optRxNodeInputPowerStatus
					ValueStatus,
				optRxNodePsuStatus
					INTEGER,
				optRxNodeLidStatus
					INTEGER,
				optRxNodeLastResponse
					INTEGER,
				optRxNodeStatus
					INTEGER
			 }

		-- 1.3.6.1.4.1.3715.100.12.10.1.1
		optRxNodeId OBJECT-TYPE
			SYNTAX INTEGER (1..32)
			ACCESS read-only
			STATUS mandatory
			DESCRIPTION
				"Third index to the table. If only one node is monitored
				by each receiver, opRxNodeId 1 is used.
				"
			::= { optRxNodeMonitoringEntry 1 }

		
		-- 1.3.6.1.4.1.3715.100.12.10.1.2
		optRxNodeCpuStatus OBJECT-TYPE
			SYNTAX INTEGER
				{
				normal(1),
				internalError(2),
				resetOccurred(3)
				}
			ACCESS read-only
			STATUS mandatory
			DESCRIPTION
				"Node CPU status:
				1 = normal
				2 = internal error
				3 = reset occurred"
			::= { optRxNodeMonitoringEntry 2 }

		
		-- 1.3.6.1.4.1.3715.100.12.10.1.4
		optRxNodeTempStatus OBJECT-TYPE
			SYNTAX ValueStatus
			ACCESS read-only
			STATUS mandatory
			DESCRIPTION
				"Node internal temperature status:
				1 = normal
				2 = HiHi
				3 = Hi
				4 = Lo
				5 = LoLo"
			::= { optRxNodeMonitoringEntry 4 }

		
		-- 1.3.6.1.4.1.3715.100.12.10.1.6
		optRxNodeLaserCurrentStatus OBJECT-TYPE
			SYNTAX ValueStatus
			ACCESS read-only
			STATUS mandatory
			DESCRIPTION
				"Node laser bias current status:
				1 = normal
				2 = HiHi
				3 = Hi
				4 = Lo
				5 = LoLo"
			::= { optRxNodeMonitoringEntry 6 }

		
		-- 1.3.6.1.4.1.3715.100.12.10.1.8
		optRxNodeNoiseLevelStatus OBJECT-TYPE
			SYNTAX ValueStatus
			ACCESS read-only
			STATUS mandatory
			DESCRIPTION
				"Node noise level status:
				1 = normal
				2 = HiHi
				3 = Hi
				4 = Lo
				5 = LoLo"
			::= { optRxNodeMonitoringEntry 8 }

		
		-- 1.3.6.1.4.1.3715.100.12.10.1.9
		optRxNodeRfOutput1Status OBJECT-TYPE
			SYNTAX ValueStatus
			ACCESS read-only
			STATUS mandatory
			DESCRIPTION
				"Node RF output 1 status:
				1 = normal
				2 = HiHi
				3 = Hi
				4 = Lo
				5 = LoLo"
			::= { optRxNodeMonitoringEntry 9 }

		
		-- 1.3.6.1.4.1.3715.100.12.10.1.11
		optRxNodeRfOutput2Status OBJECT-TYPE
			SYNTAX ValueStatus
			ACCESS read-only
			STATUS mandatory
			DESCRIPTION
				"Node RF output 2 status:
				1 = normal
				2 = HiHi
				3 = Hi
				4 = Lo
				5 = LoLo"
			::= { optRxNodeMonitoringEntry 11 }

		
		-- 1.3.6.1.4.1.3715.100.12.10.1.13
		optRxNodeInputPowerStatus OBJECT-TYPE
			SYNTAX ValueStatus
			ACCESS read-only
			STATUS mandatory
			DESCRIPTION
				"Node optical input power status:
				1 = normal
				2 = HiHi
				3 = Hi
				4 = Lo
				5 = LoLo"
			::= { optRxNodeMonitoringEntry 13 }

		
		-- 1.3.6.1.4.1.3715.100.12.10.1.16
		optRxNodePsuStatus OBJECT-TYPE
			SYNTAX INTEGER
				{
				normal(1),
				error(2)
				}
			ACCESS read-only
			STATUS mandatory
			DESCRIPTION
				"Node power supply status:
				1 = normal
				2 = error"
			::= { optRxNodeMonitoringEntry 16 }

		
		-- 1.3.6.1.4.1.3715.100.12.10.1.17
		optRxNodeLidStatus OBJECT-TYPE
			SYNTAX INTEGER
				{
				closed(1),
				open(2)
				}
			ACCESS read-only
			STATUS mandatory
			DESCRIPTION
				"Node lid status:
				1 = closed
				2 = open"
			::= { optRxNodeMonitoringEntry 17 }

		
		-- 1.3.6.1.4.1.3715.100.12.10.1.19
		optRxNodeLastResponse OBJECT-TYPE
			SYNTAX INTEGER
			ACCESS read-only
			STATUS mandatory
			DESCRIPTION
				"Seconds since last response received from node.
				
				Unit 1 s.
				
				-1, if no response from device received."
			::= { optRxNodeMonitoringEntry 19 }

		
		-- 1.3.6.1.4.1.3715.100.12.10.1.99
		optRxNodeStatus OBJECT-TYPE
			SYNTAX INTEGER
				{
				optRxNodeStatusCommunicatingOk(1),
				optRxNodeStatusCommunicatingNotOk(2),
				optRxNodeStatusOther(5),
				optRxNodeStatusUnknown(6),
				optRxNodeStatusNA(7)
				}
			ACCESS read-only
			STATUS mandatory
			DESCRIPTION
				"Communication from node to receiver status.
				1: Node communicating ok.
				2: Node not communicating.
				5: Node communication status other.
				6: Node communication status unknown.
				7: Node communication status not available."
			::= { optRxNodeMonitoringEntry 99 }

		
-- Optical amplifier objects
		-- 1.3.6.1.4.1.3715.100.13
		opticalAmplifier OBJECT IDENTIFIER ::= { functional 13 }

		
		-- 1.3.6.1.4.1.3715.100.13.1
		optAmpTable OBJECT-TYPE
			SYNTAX SEQUENCE OF OptAmpEntry
			ACCESS not-accessible
			STATUS mandatory
			::= { opticalAmplifier 1 }

		
		-- 1.3.6.1.4.1.3715.100.13.1.1
		optAmpEntry OBJECT-TYPE
			SYNTAX OptAmpEntry
			ACCESS not-accessible
			STATUS mandatory
			INDEX { moduleId }
			::= { optAmpTable 1 }

		
		OptAmpEntry ::=
			SEQUENCE { 
				optAmpGain
					INTEGER,
				optAmpChannelInputPower
					INTEGER,
				optAmpChannelOutputPower
					INTEGER,
				optAmpNrOfChannels
					INTEGER,
				optAmpPowerUnit
					INTEGER,
				optAmpOutputPowerOffset
					INTEGER,
				optAmpPumpControlStatus
					INTEGER,
				optAmptOutputPowerStatus
					ValueStatus
			 }

		-- 1.3.6.1.4.1.3715.100.13.1.1.1
		optAmpGain OBJECT-TYPE
			SYNTAX INTEGER
			ACCESS read-only
			STATUS mandatory
			DESCRIPTION
				"Amplifier gain value. Unit 0.01 dB."
			::= { optAmpEntry 1 }

		
		-- 1.3.6.1.4.1.3715.100.13.1.1.2
		optAmpChannelInputPower OBJECT-TYPE
			SYNTAX INTEGER
			ACCESS read-only
			STATUS mandatory
			DESCRIPTION
				"Optical intput power per channel. The value is given 
				in the units defined by optAmpPowerUnit object."
			::= { optAmpEntry 2 }

		
		-- 1.3.6.1.4.1.3715.100.13.1.1.4
		optAmpChannelOutputPower OBJECT-TYPE
			SYNTAX INTEGER
			ACCESS read-only
			STATUS mandatory
			DESCRIPTION
				"Optical output power per channel. The value is given 
				in the units defined by optAmpPowerUnit object."
			::= { optAmpEntry 4 }

		
		-- 1.3.6.1.4.1.3715.100.13.1.1.5
		optAmpNrOfChannels OBJECT-TYPE
			SYNTAX INTEGER (1..200)
			ACCESS read-write
			STATUS mandatory
			DESCRIPTION
				"Number of optical channels in use. This value is used 
				to calculate the optical power per channel value."
			::= { optAmpEntry 5 }

		
		-- 1.3.6.1.4.1.3715.100.13.1.1.6
		optAmpPowerUnit OBJECT-TYPE
			SYNTAX INTEGER
				{
				dBm(1),
				mW(2)
				}
			ACCESS read-write
			STATUS mandatory
			DESCRIPTION
				"Power measurement unit:
				1 = dBm
				2 = mW
				
				"
			::= { optAmpEntry 6 }

		
		-- 1.3.6.1.4.1.3715.100.13.1.1.7
		optAmpOutputPowerOffset OBJECT-TYPE
			SYNTAX INTEGER
			ACCESS read-write
			STATUS mandatory
			DESCRIPTION
				"Output power fine adjustment. Unit 0,01 %."
			::= { optAmpEntry 7 }

		
		-- 1.3.6.1.4.1.3715.100.13.1.1.8
		optAmpPumpControlStatus OBJECT-TYPE
			SYNTAX INTEGER
				{
				normal(1),
				minimum(2),
				maximum(3)
				}
			ACCESS read-only
			STATUS mandatory
			DESCRIPTION
				"Pump laser control status:
				1 = normal
				2 = minimum attenuation
				3 = maximum attenuation
				"
			::= { optAmpEntry 8 }

		
		-- 1.3.6.1.4.1.3715.100.13.1.1.9
		optAmptOutputPowerStatus OBJECT-TYPE
			SYNTAX ValueStatus
			ACCESS read-only
			STATUS mandatory
			DESCRIPTION
				"Output power status:
				1 = normal
				2 = HiHi
				3 = Hi
				4 = Lo
				5 = LoLo
				"
			::= { optAmpEntry 9 }

		
		-- 1.3.6.1.4.1.3715.100.14
		rfAmplifier OBJECT IDENTIFIER ::= { functional 14 }

		
		-- 1.3.6.1.4.1.3715.100.14.1
		rfAmplifierControl OBJECT-TYPE
			SYNTAX INTEGER
				{
				on(1),
				off(2)
				}
			ACCESS read-write
			STATUS mandatory
			DESCRIPTION
				"Amplifier control:
				1 = ON
				2 = OFF"
			::= { rfAmplifier 1 }

		
		-- 1.3.6.1.4.1.3715.100.14.2
		rfAmpGain OBJECT-TYPE
			SYNTAX INTEGER
			ACCESS read-write
			STATUS mandatory
			DESCRIPTION
				"Amplifier gain control value. Unit 0.01 dB"
			::= { rfAmplifier 2 }

		
		-- 1.3.6.1.4.1.3715.100.14.3
		rfAmpSlope OBJECT-TYPE
			SYNTAX INTEGER
			ACCESS read-write
			STATUS mandatory
			DESCRIPTION
				"Amplifier slope control value. Unit 0.01 dB"
			::= { rfAmplifier 3 }

		
		-- 1.3.6.1.4.1.3715.100.14.4
		rfAmpRfLevel OBJECT-TYPE
			SYNTAX INTEGER
			ACCESS read-only
			STATUS mandatory
			DESCRIPTION
				"RF power relative level. Unit 0.01 dB"
			::= { rfAmplifier 4 }

		
		-- 1.3.6.1.4.1.3715.100.14.5
		rfAmpRfLevelStatus OBJECT-TYPE
			SYNTAX INTEGER
				{
				levelNormal(1),
				levelLOLO(2),
				levelLo(3),
				levelHi(4),
				levelHIHI(5)
				}
			ACCESS read-only
			STATUS mandatory
			::= { rfAmplifier 5 }

		
	
	END

--
-- TELESTE-HFCOPTICS-MIB.mib
--
