--
-- TELESTE-FUNCTIONAL-RPD-MIB.mib
-- MIB generated by MG-SOFT Visual MIB Builder 2021 (64-bit) Version 15.00  Build 1510
-- Thursday, October 06, 2022 at 15:50:19
--

-- ****************************************************************************
-- Copyright (c) 2003-2014 by:
-- 
-- Teleste Corporation
-- Seponkatu 1
-- FIN-20660 Littoinen, Finland
-- tel. +358 2 2605 611
-- url: http://www.teleste.com
-- 
-- Module Name: TELESTE-FUNCTIONAL-RPD-MIB
-- 
-- Description: MIB module describing Teleste RPD module objects
-- 
-- Revision History:
-- -----------------
-- 24, 6.10.2022, Sami Kuusisto
-- - Added detectedRpdGeneration.
-- 
-- 23, 4.10.2022, Sami Kuusisto
-- - Added new enums to detectedRpdType and rpdType.
-- 
-- 22, 4.10.2022, Sami Kuusisto
-- - Added rpdShelfPsuFailureBits.
-- 
-- 21, 5.9.2022, Sami Kuusisto
-- - Fixed rpdShelfPsuInstallationPosition enum names.
-- 
-- 20, 5.9.2022, Sami Kuusisto
-- - Added new enum rpdType2Ds4Us(6) to rpdType.
-- 
-- 19, 11.5.2022, Sami Kuusisto
-- - Added rpdShelfPsu.
-- 
-- 18, 29.10.2021, Sami Kuusisto
-- - Fixed rpdRemotePortInfomationWaveLength scaling example. Scale itselft (0.001 nm is correct), but example used worng scale.
-- 
-- 17, 23.3.2021, Sami Kuusisto
-- - Added new field to upsStatusData.
-- 
-- 16, 18.3.2021, Sami Kuusisto
-- - Added rpdUps and rpdUpsEventLog tree.
-- 
-- 15, 21.1.2021, Sami Kuusisto
-- - Added rpdPsu1Status and rpdPsu2Status.
-- 
-- 14, 20.11.2020, Sami Kuusisto
-- - Added rpdInputVoltage and rpdInputCurrent.
-- 
-- 13, 13.11.2020, Sami Kuusisto
-- - Updated rpdDsChannelsTableData0-399 type field description.
-- 
-- 12, 28.9.2020, Sami Kuusisto
-- - Added note about value 0, temperature information not available, to rpdRemotePortInfomationTemperature.
-- 
-- 11, 27.4.2020, Sami Kuusisto
-- - Added rpdLocalPortMacAddress and rpdRemotePortInfomationMacAddress.
-- 
-- 10, 4.11.2109, Sami Kuusisto
-- - Added rpdDsChannelsNumberOfChannels and rpdUsChannelsNumberOfChannels.
-- 
-- 9, 1.11.2019, Sami Kuusisto
-- - Added rpdNodeOutputPower1/2/3/4.
-- 
-- 8, 18.10.2019, 21.10.2019, Sami Kuusisto
-- - Updated v7 stuff.
-- 
-- 7, 17.10.2019, Sami Kuusisto
-- - Added RPD status (general, port, DS/US channels, log) information.
-- 
-- 6, 20.09.2019, Sami Kuusisto
-- - Added relativeHumidity.
-- 
-- 5, 19.09.2019, Sami Kuusisto
-- - Added rpdRfCables section.
-- 
-- 4, 23.11.2017, Sami Kuusisto
-- - Moved IP addresses under rpdIpAddresses and added local/remoteIPv4/6Addresses.
-- 
-- 3, 7.11.2017, Sami Kuusisto
-- - Added rpdIpv4Address, rpdIpv4NetMask, rpdIpv4Gateway and rpdIpv6Address.
-- 
-- 2, 19.9.2017, Sami Kuusisto
-- - Added rpdSysDescription, rpdType, dpdType.
-- 
-- 1, 21.2.2017, Sami Kuusisto
-- - Initial version
-- 
-- ****************************************************************************

	TELESTE-FUNCTIONAL-RPD-MIB DEFINITIONS ::= BEGIN
 
		IMPORTS
			OBJECT-TYPE			
				FROM RFC-1212			
			IpAddress			
				FROM RFC1155-SMI			
			functional, TPhysAddress			
				FROM TELESTE-ROOT-MIB;
	
	
	
--
-- Node definitions
--
	
		-- 1.3.6.1.4.1.3715.100.103
		rpd OBJECT IDENTIFIER ::= { functional 103 }

		
-- Transponder RF modem specific objects
-- 
		-- 1.3.6.1.4.1.3715.100.103.1
		rpdStatus OBJECT IDENTIFIER ::= { rpd 1 }

		
		-- 1.3.6.1.4.1.3715.100.103.1.1
		rpdCommonStatus OBJECT-TYPE
			SYNTAX INTEGER
				{
				rpdCommonStatusOk(1),
				rpdCommonStatusError(2)
				}
			ACCESS read-only
			STATUS mandatory
			DESCRIPTION
				"RPD common status.
				
				1: RPD module ok
				2: RPD module error. E.g. node can't communicate with RPD module."
			::= { rpdStatus 1 }

		
		-- 1.3.6.1.4.1.3715.100.103.1.2
		rpdRemoteLinkStatus OBJECT-TYPE
			SYNTAX INTEGER
				{
				rpdRemoteLinkStatusLinkUp(1),
				rpdRemoteLinkStatusLinkDown(2)
				}
			ACCESS read-only
			STATUS mandatory
			DESCRIPTION
				"RPD remote link status.
				
				1: Remote link up.
				2: Remote link down.
				"
			::= { rpdStatus 2 }

		
		-- 1.3.6.1.4.1.3715.100.103.1.3
		rpdSysDescription OBJECT-TYPE
			SYNTAX OCTET STRING
			ACCESS read-only
			STATUS mandatory
			DESCRIPTION
				"This object contains textual information about RPD module.
				
				Format: Manufacturer HwModel <<HW_REV: XX.X; VENDOR: Vendor; BOOTR: 1.2.3; SW_REV: 4.5.6; MODEL: HwModel; SERIAL: SK12345678; BOOTCOUNT: #; UPTIME: fulldays# d hh:mm:ss; TOTAL_UPTIME: fulldays#; DOWNSTREAMS: NumberOfDownStreams; UPSTREAMS: NumberOFUpStreams>>
				
				Keywords are UPPER CASE and any of them can be omitted and they can be used in any order.
				
				Example: Teleste RPD123 <<HW_REV: A1.0; VENDOR: Teleste; SW_REV: 1.2; MODEL: RPD123; SERIAL: KL12341737; BOOTCOUNT: 78; UPTIME: 22 d 11:22:33; TOTAL_UPTIME: 47; DOWNSTREAMS: 1; UPSTREAMS: 2>>"
			::= { rpdStatus 3 }

		
		-- 1.3.6.1.4.1.3715.100.103.1.4
		rpdType OBJECT-TYPE
			SYNTAX INTEGER
				{
				rpdTypeNone(1),
				rpdType1Ds1Us(2),
				rpdType1Ds2Us(3),
				rpdType1Ds4Us(4),
				rpdType2Ds2Us(5),
				rpdType2Ds4Us(6),
				rpdType2Ds1Us(7)
				}
			ACCESS read-write
			STATUS mandatory
			DESCRIPTION
				"Installed RPD module type.
				1: None
				2: 1xDS, 1xUS 
				3: 1xDS, 2xUS
				4: 1xDS, 4xUS
				5: 2xDS, 2xUS
				6: 2xDS, 4xUS
				7: 2xDS, 1xUS"
			::= { rpdStatus 4 }

		
		-- 1.3.6.1.4.1.3715.100.103.1.5
		dpdType OBJECT-TYPE
			SYNTAX INTEGER
				{
				dpdTypeNone(1),
				dpdTypeTBD(2)
				}
			ACCESS read-write
			STATUS mandatory
			DESCRIPTION
				"Installed DPD type
				1: None
				2: TBD"
			::= { rpdStatus 5 }

		
		-- 1.3.6.1.4.1.3715.100.103.1.6
		humidity OBJECT-TYPE
			SYNTAX INTEGER
			ACCESS read-only
			STATUS mandatory
			DESCRIPTION
				"Measured humidity %. Unit 0.01 %."
			::= { rpdStatus 6 }

		
		-- 1.3.6.1.4.1.3715.100.103.1.7
		detectedRpdType OBJECT-TYPE
			SYNTAX INTEGER
				{
				detectedRpdTypeNone(1),
				detectedRpdType1Ds1Us(2),
				detectedRpdType1Ds2Us(3),
				detectedRpdType1Ds4Us(4),
				detectedRpdType2Ds2Us(5),
				detectedRpdType2Ds4Us(6),
				detectedRpdType2Ds1Us(7)
				}
			ACCESS read-only
			STATUS mandatory
			DESCRIPTION
				"Detected RPD module type.
				1: None
				2: 1xDS, 1xUS 
				3: 1xDS, 2xUS
				4: 1xDS, 4xUS
				5: 2xDS, 2xUS
				6: 2xDS, 4xUS
				7: 2xDS, 1xUS"
			::= { rpdStatus 7 }

		
		-- 1.3.6.1.4.1.3715.100.103.1.8
		rpdTemperature OBJECT-TYPE
			SYNTAX INTEGER
			ACCESS read-only
			STATUS mandatory
			DESCRIPTION
				"RPD's internal temperature.
				Unit 0.01 oC.
				
				See also rpdTemperatureStatus."
			::= { rpdStatus 8 }

		
		-- 1.3.6.1.4.1.3715.100.103.1.9
		rpdTemperatureStatus OBJECT-TYPE
			SYNTAX INTEGER
				{
				temperatureStatusUninitialized(0),
				temperatureStatusNormal(1),
				temperatureStatusHIHI(2),
				temperatureStatusHi(3),
				temperatureStatusLo(4),
				temperatureStatusLOLO(5)
				}
			ACCESS read-only
			STATUS mandatory
			DESCRIPTION
				"RPD's internal temperature status.
				Limits are not editable or visible.
				
				0: Uninitialized: rpdTemperature value is not relevant.
				1: Normal
				2: HIHI: Temperature is over HIHI limit
				3: Hi: Temperature is over Hi limit
				4: Lo: Tempearture is below Lo limit
				5: LOLO: Temperature is below LOLO limit"
			::= { rpdStatus 9 }

		
		-- 1.3.6.1.4.1.3715.100.103.1.10
		rpdBootUpProcessStatusBits OBJECT-TYPE
			SYNTAX INTEGER
			ACCESS read-only
			STATUS mandatory
			DESCRIPTION
				"RPD's boot-up process status in bit mask. See also rpdBootUpProcessStatusBitsMask.
				When bit is set '1': status is ok.
				When bit is reset '0': status is not ok (nok).
				
				0x0001: Local RPD init
				0x0002: CIN link up
				0x0004: Network authentication (802.1x)
				0x0008: reserved
				0x0010: IP address assignment (DHCP)
				0x0020: IPv4 address
				0x0040: IPv6 address
				0x0080: Get ToD
				0x0100: IPSec
				0x0200: TCP init
				0x0400: GCP INIT IRA
				0x0800: GCP INIT CFG
				0x1000: Connected to principal core
				0x2000: Software update in progress
				0x4000: Configuration complete
				0x8000: Operational"
			::= { rpdStatus 10 }

		
		-- 1.3.6.1.4.1.3715.100.103.1.11
		rpdBootUpProcessStatusBitsMask OBJECT-TYPE
			SYNTAX INTEGER
			ACCESS read-only
			STATUS mandatory
			DESCRIPTION
				"RPD's boot-up process status bits mask in bit mask. See also rpdBootUpProcessStatusBits.
				When mask bit is set '1': bit in rpdBootUpProcessStatusBits should be checked.
				When mask bit is reset '0': bit in rpdBootUpProcessStatusBits should be ignored (or considered ok regardless rpdBootUpProcessStatusBits value)."
			::= { rpdStatus 11 }

		
		-- 1.3.6.1.4.1.3715.100.103.1.12
		rpdSwStatusBits OBJECT-TYPE
			SYNTAX INTEGER
			ACCESS read-write
			STATUS mandatory
			DESCRIPTION
				"RPD's boot-up process status in bit mask. See also rpdBootUpProcessStatusBitsMask.
				When bit is set '1': status is ok.
				When bit is reset '0': status is not ok (nok).
				
				0x0001: PTP unqaulified
				0x0002: PTP lock acquisition
				0x0004: PTP frequency locked
				0x0008: PTP time locked
				0x0010: PTP holdover in spec
				0x0020: PTP holdover out of spec
				0x0040: reserved
				0x0080: reserved
				0x0100: Reboot in progress
				0x0200: GCP keepalive
				0x0400: reserved
				0x0800: reserved
				0x1000: Auxilliary cores
				0x2000: L2TP sessions
				0x4000: reserved
				0x8000: reserved"
			::= { rpdStatus 12 }

		
		-- 1.3.6.1.4.1.3715.100.103.1.13
		rpdSwStatusBitsMask OBJECT-TYPE
			SYNTAX INTEGER
			ACCESS read-write
			STATUS mandatory
			DESCRIPTION
				"RPD's boot-up process status bits mask in bit mask. See also rpdSwStatusBits.
				When mask bit is set '1': bit in rpdSwStatusBits should be checked.
				When mask bit is reset '0': bit in rpdSwStatusBits should be ignored (or considered ok regardless rpdSwStatusBits value)."
			::= { rpdStatus 13 }

		
		-- 1.3.6.1.4.1.3715.100.103.1.14
		rpdHwStatusBits OBJECT-TYPE
			SYNTAX INTEGER
			ACCESS read-write
			STATUS mandatory
			DESCRIPTION
				"RPD's boot-up process status in bit mask. See also rpdBootUpProcessStatusBitsMask.
				When bit is set '1': status is ok.
				When bit is reset '0': status is not ok (nok).
				
				0x0001: Voltages
				0x0002: HeartBeat (between RPD and cortex)
				0x0004…0x8000: reserved"
			::= { rpdStatus 14 }

		
		-- 1.3.6.1.4.1.3715.100.103.1.15
		rpdHwStatusBitsMask OBJECT-TYPE
			SYNTAX INTEGER
			ACCESS read-write
			STATUS mandatory
			DESCRIPTION
				"RPD's boot-up process status bits mask in bit mask. See also rpdHwStatusBits.
				When mask bit is set '1': bit in rpdHwStatusBits should be checked.
				When mask bit is reset '0': bit in rpdHwStatusBits should be ignored (or considered ok regardless rpdHwStatusBits value)."
			::= { rpdStatus 15 }

		
		-- 1.3.6.1.4.1.3715.100.103.1.16
		rpdDsUsInfo OBJECT-TYPE
			SYNTAX INTEGER
			ACCESS read-only
			STATUS mandatory
			DESCRIPTION
				"RPD's current DS and US status and capabilities.
				
				Downstream (DS)
				0x0001: When bit is 1: DS1 active/enabled, when bit is 0: DS1 not in use/disabled
				0x0002: When bit is 1: DS2 active/enabled, when bit is 0: DS2 not in use/disabled
				0x0004: When bit is 1: DS3 active/enabled, when bit is 0: DS3 not in use/disabled
				0x0008: When bit is 1: DS4 active/enabled, when bit is 0: DS4 not in use/disabled
				0x0010: When bit is 1: DS1 exists (can be enabled), when bit is 0: DS1 doesn't exists (can't be enabled)
				0x0020: When bit is 1: DS2 exists (can be enabled), when bit is 0: DS2 doesn't exists (can't be enabled)
				0x0040: When bit is 1: DS3 exists (can be enabled), when bit is 0: DS3 doesn't exists (can't be enabled)
				0x0080: When bit is 1: DS4 exists (can be enabled), when bit is 0: DS4 doesn't exists (can't be enabled)
				
				Upstream (US)
				0x0100: When bit is 1: DS1 active/enabled, when bit is 0: DS1 not in use/disabled
				0x0200: When bit is 1: DS2 active/enabled, when bit is 0: DS2 not in use/disabled
				0x0400: When bit is 1: DS3 active/enabled, when bit is 0: DS3 not in use/disabled
				0x0800: When bit is 1: DS4 active/enabled, when bit is 0: DS4 not in use/disabled
				0x1000: When bit is 1: DS1 exists (can be enabled), when bit is 0: DS1 doesn't exists (can't be enabled)
				0x2000: When bit is 1: DS2 exists (can be enabled), when bit is 0: DS2 doesn't exists (can't be enabled)
				0x4000: When bit is 1: DS3 exists (can be enabled), when bit is 0: DS3 doesn't exists (can't be enabled)
				0x8000: When bit is 1: DS4 exists (can be enabled), when bit is 0: DS4 doesn't exists (can't be enabled)"
			::= { rpdStatus 16 }

		
		-- 1.3.6.1.4.1.3715.100.103.1.17
		rpdCurrentTime OBJECT-TYPE
			SYNTAX INTEGER
			ACCESS read-only
			STATUS mandatory
			DESCRIPTION
				"RPD's current time in posix format. Unit 1 s. Epoch 1.1.1970."
			::= { rpdStatus 17 }
-- RPD's current time in posix format. Unit 1 s. Epoch 1.1.1970.
		
		-- 1.3.6.1.4.1.3715.100.103.1.18
		rpdLastResponse OBJECT-TYPE
			SYNTAX INTEGER
			ACCESS read-only
			STATUS mandatory
			DESCRIPTION
				"Number of seconds since last packet received from RPD by node. Unit 1 s.
				Node provides this information. 
				
				0: no packet received from RPD by node (yet), 
				1-65534: number of seconds since last received packet, 
				65535: communication problem."
			::= { rpdStatus 18 }

		
		-- 1.3.6.1.4.1.3715.100.103.1.19
		rpdDelayUntilNextReboot OBJECT-TYPE
			SYNTAX INTEGER
			ACCESS read-only
			STATUS mandatory
			DESCRIPTION
				"RPD informs when RPD reboots next time. Unit 1 s.
				See also rpdAutomaticReconnectRebootTimeout.
				
				0: Unknown (typically: node has not yet received information from RPD), 
				1-65534: number of seconds until next RPD reboot, 
				65535: No reboot scheduled."
			::= { rpdStatus 19 }

		
		-- 1.3.6.1.4.1.3715.100.103.1.20
		rpdAutomaticReconnectRebootTimeout OBJECT-TYPE
			SYNTAX INTEGER
			ACCESS read-only
			STATUS mandatory
			DESCRIPTION
				"RPD informs the length of the time period that RPD tries to get online.
				See also  rpdDelayUntilNextReboot.
				
				0: Unknown (typically: node has not yet received information from RPD), 
				1-65534: number of seconds RPD tries to get online until RPD makes reboot, 
				65535: automatic reboot disabled. See also rpdDelayUntilNextReboot."
			::= { rpdStatus 20 }

		
		-- 1.3.6.1.4.1.3715.100.103.1.21
		rpdUptimeDays OBJECT-TYPE
			SYNTAX INTEGER
			ACCESS read-only
			STATUS mandatory
			DESCRIPTION
				"RPD's uptime in full days. Unit 1 day."
			::= { rpdStatus 21 }

		
		-- 1.3.6.1.4.1.3715.100.103.1.22
		rpdUptimeSeconds OBJECT-TYPE
			SYNTAX INTEGER
			ACCESS read-only
			STATUS mandatory
			DESCRIPTION
				"RPD's current day's uptime in seconds. Unit 1 s."
			::= { rpdStatus 22 }

		
		-- 1.3.6.1.4.1.3715.100.103.1.23
		rpdTotalUptimeDays OBJECT-TYPE
			SYNTAX INTEGER
			ACCESS read-only
			STATUS mandatory
			DESCRIPTION
				"RPD's cumulative uptime in full days. Unit 1 day."
			::= { rpdStatus 23 }

		
		-- 1.3.6.1.4.1.3715.100.103.1.24
		rpdResetCount OBJECT-TYPE
			SYNTAX INTEGER
			ACCESS read-only
			STATUS mandatory
			DESCRIPTION
				"RPD's number of boot-ups/resets. Unit 1 boot-up/reset."
			::= { rpdStatus 24 }

		
		-- 1.3.6.1.4.1.3715.100.103.1.25
		rpdInputVoltage OBJECT-TYPE
			SYNTAX INTEGER
			ACCESS read-only
			STATUS mandatory
			DESCRIPTION
				"RPD module input voltage measured by RPD module.
				Unit 0.01 V.
				
				Exact 0 (0x0000) means that measurement is unavailable."
			::= { rpdStatus 25 }

		
		-- 1.3.6.1.4.1.3715.100.103.1.26
		rpdInputCurrent OBJECT-TYPE
			SYNTAX INTEGER
			ACCESS read-only
			STATUS mandatory
			DESCRIPTION
				"RPD module input current measured by RPD module.
				Unit 0.01 A.
				
				Exact 0 (0x0000) means that measurement is unavailable."
			::= { rpdStatus 26 }

		
		-- 1.3.6.1.4.1.3715.100.103.1.27
		rpdPsu1Status OBJECT-TYPE
			SYNTAX INTEGER
				{
				rpdPsu1StatusOk(1),
				rpdPsu1StatusFailure(2),
				rpdPsu1StatusNA(3)
				}
			ACCESS read-only
			STATUS mandatory
			DESCRIPTION
				"RPD Power supply 1 status.
				1: OK
				2: Failure
				3: Power supply 1 status not available."
			::= { rpdStatus 27 }

		
		-- 1.3.6.1.4.1.3715.100.103.1.28
		rpdPsu2Status OBJECT-TYPE
			SYNTAX INTEGER
				{
				rpdPsu2StatusOk(1),
				rpdPsu2StatusFailure(2),
				rpdPsu2StatusNA(3)
				}
			ACCESS read-only
			STATUS mandatory
			DESCRIPTION
				"RPD Power supply 2 status.
				1: OK
				2: Failure
				3: Power supply 2 status not available."
			::= { rpdStatus 28 }

		
		-- 1.3.6.1.4.1.3715.100.103.1.29
		detectedRpdGeneration OBJECT-TYPE
			SYNTAX INTEGER
				{
				detectedRpdGeneration1st(1),
				detectedRpdGeneration2nd(2),
				detectedRpdGenerationUnknown(99)
				}
			ACCESS read-only
			STATUS mandatory
			DESCRIPTION
				"Detected RPD generation
				1: 1st generation
				2: 2nd generation
				...
				99: generation unknown"
			::= { rpdStatus 29 }

		
		-- 1.3.6.1.4.1.3715.100.103.2
		rpdIpAddresses OBJECT IDENTIFIER ::= { rpd 2 }

		
		-- 1.3.6.1.4.1.3715.100.103.2.1
		nodePrivateIpv4Address OBJECT-TYPE
			SYNTAX IpAddress
			ACCESS read-only
			STATUS mandatory
			DESCRIPTION
				"Private IPv4 address of RPD node."
			::= { rpdIpAddresses 1 }

		
		-- 1.3.6.1.4.1.3715.100.103.2.2
		nodePrivateIpv4NetMask OBJECT-TYPE
			SYNTAX IpAddress
			ACCESS read-only
			STATUS mandatory
			DESCRIPTION
				"Private IPv4 netmask of RPD node."
			::= { rpdIpAddresses 2 }

		
		-- 1.3.6.1.4.1.3715.100.103.2.3
		nodePrivateIpv4Gateway OBJECT-TYPE
			SYNTAX IpAddress
			ACCESS read-only
			STATUS mandatory
			DESCRIPTION
				"Private IPv4 gateway address used by RPD node."
			::= { rpdIpAddresses 3 }

		
		-- 1.3.6.1.4.1.3715.100.103.2.4
		localManagementIpv4Address OBJECT-TYPE
			SYNTAX IpAddress
			ACCESS read-only
			STATUS mandatory
			DESCRIPTION
				"Local IPv4 address used for node management."
			::= { rpdIpAddresses 4 }

		
		-- 1.3.6.1.4.1.3715.100.103.2.5
		remoteManagementIpv4Address OBJECT-TYPE
			SYNTAX IpAddress
			ACCESS read-only
			STATUS mandatory
			DESCRIPTION
				"Remote IPv4 address used for node management."
			::= { rpdIpAddresses 5 }

		
		-- 1.3.6.1.4.1.3715.100.103.2.6
		localManagementIpv6Address OBJECT-TYPE
			SYNTAX OCTET STRING
			ACCESS read-only
			STATUS mandatory
			DESCRIPTION
				"Local IPv6 address used for node management.
				Format: 16 hex bytes (uint8_t[16])."
			::= { rpdIpAddresses 6 }

		
		-- 1.3.6.1.4.1.3715.100.103.2.7
		remoteManagementIpv6Address OBJECT-TYPE
			SYNTAX OCTET STRING
			ACCESS read-only
			STATUS mandatory
			DESCRIPTION
				"Remote IPv6 address used for node management.
				Format: 16 hex bytes (uint8_t[16])."
			::= { rpdIpAddresses 7 }

		
		-- 1.3.6.1.4.1.3715.100.103.3
		rpdRfCables OBJECT IDENTIFIER ::= { rpd 3 }

		
		-- 1.3.6.1.4.1.3715.100.103.3.1
		rpdRfCableAtNodeDs1Connector OBJECT-TYPE
			SYNTAX INTEGER
				{
				short(1),
				rpdDs1Output(2),
				rpdDs2Output(3),
				rpdDs3Output(4),
				rpdDs4Output(5),
				rpdDpdInput(6),
				rpdUs1Input(7),
				rpdUs2Input(8),
				rpdUs3Input(9),
				rpdUs4Input(10),
				open(12),
				unknown(14),
				notAvailable(15)
				}
			ACCESS read-only
			STATUS mandatory
			DESCRIPTION
				"Detected RPD RF cable at node DS1 connector: 
				1: Short, 
				2: DS1 output, 
				3: DS2 output, 
				4: DS3 output, 
				5: DS4 output, 
				6: DPD input, 
				7: US1 input, 
				8: US2 input, 
				9: US3 input, 
				10: US4 input, 
				11: reserved, 
				12: open, 
				14: Unknown, 
				15: N/A."
			::= { rpdRfCables 1 }

		
		-- 1.3.6.1.4.1.3715.100.103.3.2
		rpdRfCableAtNodeDs2Connector OBJECT-TYPE
			SYNTAX INTEGER
				{
				short(1),
				rpdDs1Output(2),
				rpdDs2Output(3),
				rpdDs3Output(4),
				rpdDs4Output(5),
				rpdDpdInput(6),
				rpdUs1Input(7),
				rpdUs2Input(8),
				rpdUs3Input(9),
				rpdUs4Input(10),
				open(12),
				unknown(14),
				notAvailable(15)
				}
			ACCESS read-only
			STATUS mandatory
			DESCRIPTION
				"Detected RPD RF cable at node DS2 connector: 
				1: Short, 
				2: DS1 output, 
				3: DS2 output, 
				4: DS3 output, 
				5: DS4 output, 
				6: DPD input, 
				7: US1 input, 
				8: US2 input, 
				9: US3 input, 
				10: US4 input, 
				11: reserved, 
				12: open, 
				14: Unknown, 
				15: N/A."
			::= { rpdRfCables 2 }

		
		-- 1.3.6.1.4.1.3715.100.103.3.3
		rpdRfCableAtNodeDs3Connector OBJECT-TYPE
			SYNTAX INTEGER
				{
				short(1),
				rpdDs1Output(2),
				rpdDs2Output(3),
				rpdDs3Output(4),
				rpdDs4Output(5),
				rpdDpdInput(6),
				rpdUs1Input(7),
				rpdUs2Input(8),
				rpdUs3Input(9),
				rpdUs4Input(10),
				open(12),
				unknown(14),
				notAvailable(15)
				}
			ACCESS read-only
			STATUS mandatory
			DESCRIPTION
				"Detected RPD RF cable at node DS3 connector: 
				1: Short, 
				2: DS1 output, 
				3: DS2 output, 
				4: DS3 output, 
				5: DS4 output, 
				6: DPD input, 
				7: US1 input, 
				8: US2 input, 
				9: US3 input, 
				10: US4 input, 
				11: reserved, 
				12: open, 
				14: Unknown, 
				15: N/A."
			::= { rpdRfCables 3 }

		
		-- 1.3.6.1.4.1.3715.100.103.3.4
		rpdRfCableAtNodeDs4Connector OBJECT-TYPE
			SYNTAX INTEGER
				{
				short(1),
				rpdDs1Output(2),
				rpdDs2Output(3),
				rpdDs3Output(4),
				rpdDs4Output(5),
				rpdDpdInput(6),
				rpdUs1Input(7),
				rpdUs2Input(8),
				rpdUs3Input(9),
				rpdUs4Input(10),
				open(12),
				unknown(14),
				notAvailable(15)
				}
			ACCESS read-only
			STATUS mandatory
			DESCRIPTION
				"Detected RPD RF cable at node DS4 connector: 
				1: Short, 
				2: DS1 output, 
				3: DS2 output, 
				4: DS3 output, 
				5: DS4 output, 
				6: DPD input, 
				7: US1 input, 
				8: US2 input, 
				9: US3 input, 
				10: US4 input, 
				11: reserved, 
				12: open, 
				14: Unknown, 
				15: N/A."
			::= { rpdRfCables 4 }

		
		-- 1.3.6.1.4.1.3715.100.103.3.5
		rpdRfCableAtNodeDpdConnector OBJECT-TYPE
			SYNTAX INTEGER
				{
				short(1),
				rpdDs1Output(2),
				rpdDs2Output(3),
				rpdDs3Output(4),
				rpdDs4Output(5),
				rpdDpdInput(6),
				rpdUs1Input(7),
				rpdUs2Input(8),
				rpdUs3Input(9),
				rpdUs4Input(10),
				open(12),
				unknown(14),
				notAvailable(15)
				}
			ACCESS read-only
			STATUS mandatory
			DESCRIPTION
				"Detected RPD RF cable at node DPD connector: 
				1: Short, 
				2: DS1 output, 
				3: DS2 output, 
				4: DS3 output, 
				5: DS4 output, 
				6: DPD input, 
				7: US1 input, 
				8: US2 input, 
				9: US3 input, 
				10: US4 input, 
				11: reserved, 
				12: open, 
				14: Unknown, 
				15: N/A."
			::= { rpdRfCables 5 }

		
		-- 1.3.6.1.4.1.3715.100.103.3.6
		rpdRfCableAtNodeUs1Connector OBJECT-TYPE
			SYNTAX INTEGER
				{
				short(1),
				rpdDs1Output(2),
				rpdDs2Output(3),
				rpdDs3Output(4),
				rpdDs4Output(5),
				rpdDpdInput(6),
				rpdUs1Input(7),
				rpdUs2Input(8),
				rpdUs3Input(9),
				rpdUs4Input(10),
				open(12),
				unknown(14),
				notAvailable(15)
				}
			ACCESS read-only
			STATUS mandatory
			DESCRIPTION
				"Detected RPD RF cable at node US1 connector: 
				1: Short, 
				2: DS1 output, 
				3: DS2 output, 
				4: DS3 output, 
				5: DS4 output, 
				6: DPD input, 
				7: US1 input, 
				8: US2 input, 
				9: US3 input, 
				10: US4 input, 
				11: reserved, 
				12: open, 
				14: Unknown, 
				15: N/A."
			::= { rpdRfCables 6 }

		
		-- 1.3.6.1.4.1.3715.100.103.3.7
		rpdRfCableAtNodeUs2Connector OBJECT-TYPE
			SYNTAX INTEGER
				{
				short(1),
				rpdDs1Output(2),
				rpdDs2Output(3),
				rpdDs3Output(4),
				rpdDs4Output(5),
				rpdDpdInput(6),
				rpdUs1Input(7),
				rpdUs2Input(8),
				rpdUs3Input(9),
				rpdUs4Input(10),
				open(12),
				unknown(14),
				notAvailable(15)
				}
			ACCESS read-only
			STATUS mandatory
			DESCRIPTION
				"Detected RPD RF cable at node US2 connector: 
				1: Short, 
				2: DS1 output, 
				3: DS2 output, 
				4: DS3 output, 
				5: DS4 output, 
				6: DPD input, 
				7: US1 input, 
				8: US2 input, 
				9: US3 input, 
				10: US4 input, 
				11: reserved, 
				12: open, 
				14: Unknown, 
				15: N/A."
			::= { rpdRfCables 7 }

		
		-- 1.3.6.1.4.1.3715.100.103.3.8
		rpdRfCableAtNodeUs3Connector OBJECT-TYPE
			SYNTAX INTEGER
				{
				short(1),
				rpdDs1Output(2),
				rpdDs2Output(3),
				rpdDs3Output(4),
				rpdDs4Output(5),
				rpdDpdInput(6),
				rpdUs1Input(7),
				rpdUs2Input(8),
				rpdUs3Input(9),
				rpdUs4Input(10),
				open(12),
				unknown(14),
				notAvailable(15)
				}
			ACCESS read-only
			STATUS mandatory
			DESCRIPTION
				"Detected RPD RF cable at node US3 connector: 
				1: Short, 
				2: DS1 output, 
				3: DS2 output, 
				4: DS3 output, 
				5: DS4 output, 
				6: DPD input, 
				7: US1 input, 
				8: US2 input, 
				9: US3 input, 
				10: US4 input, 
				11: reserved, 
				12: open, 
				14: Unknown, 
				15: N/A."
			::= { rpdRfCables 8 }

		
		-- 1.3.6.1.4.1.3715.100.103.3.9
		rpdRfCableAtNodeUs4Connector OBJECT-TYPE
			SYNTAX INTEGER
				{
				short(1),
				rpdDs1Output(2),
				rpdDs2Output(3),
				rpdDs3Output(4),
				rpdDs4Output(5),
				rpdDpdInput(6),
				rpdUs1Input(7),
				rpdUs2Input(8),
				rpdUs3Input(9),
				rpdUs4Input(10),
				open(12),
				unknown(14),
				notAvailable(15)
				}
			ACCESS read-only
			STATUS mandatory
			DESCRIPTION
				"Detected RPD RF cable at node US4 connector: 
				1: Short, 
				2: DS1 output, 
				3: DS2 output, 
				4: DS3 output, 
				5: DS4 output, 
				6: DPD input, 
				7: US1 input, 
				8: US2 input, 
				9: US3 input, 
				10: US4 input, 
				11: reserved, 
				12: open, 
				14: Unknown, 
				15: N/A."
			::= { rpdRfCables 9 }

		
		-- 1.3.6.1.4.1.3715.100.103.4
		rpdLocalManagementPortInformation OBJECT IDENTIFIER ::= { rpd 4 }

		
		-- 1.3.6.1.4.1.3715.100.103.4.1
		rpdLocalPortStatus OBJECT-TYPE
			SYNTAX INTEGER
			ACCESS read-only
			STATUS mandatory
			DESCRIPTION
				"Local management (RJ-45) status
				
				1: link up, 
				2: link down, 
				3: error, 
				4: unknown, 
				5: N/A"
			::= { rpdLocalManagementPortInformation 1 }

		
		-- 1.3.6.1.4.1.3715.100.103.4.2
		rpdLocalPortBitrate OBJECT-TYPE
			SYNTAX INTEGER
			ACCESS read-only
			STATUS mandatory
			DESCRIPTION
				"Local management port (RJ-45) bitrate. Unit 1 Mbps.
				
				0: Bitrate info not available."
			::= { rpdLocalManagementPortInformation 2 }

		
		-- 1.3.6.1.4.1.3715.100.103.4.3
		rpdLocalPortMacAddress OBJECT-TYPE
			SYNTAX TPhysAddress
			ACCESS read-only
			STATUS mandatory
			DESCRIPTION
				"Local maangement port (RJ-45) MAC address. 
				If the MAC address is unknown '00.00.00.00.00.00' is returned."
			::= { rpdLocalManagementPortInformation 3 }

		
		-- 1.3.6.1.4.1.3715.100.103.5
		rpdRemotePortInformation OBJECT IDENTIFIER ::= { rpd 5 }

		
		-- 1.3.6.1.4.1.3715.100.103.5.1
		rpdRemotePortCount OBJECT-TYPE
			SYNTAX INTEGER
			ACCESS read-only
			STATUS mandatory
			DESCRIPTION
				"Number of remote ports in RPD."
			::= { rpdRemotePortInformation 1 }

		
		-- 1.3.6.1.4.1.3715.100.103.5.2
		rpdRemotePortInfomationTable OBJECT-TYPE
			SYNTAX SEQUENCE OF RpdRemotePortInfomationEntry
			ACCESS not-accessible
			STATUS mandatory
			::= { rpdRemotePortInformation 2 }

		
		-- 1.3.6.1.4.1.3715.100.103.5.2.1
		rpdRemotePortInfomationEntry OBJECT-TYPE
			SYNTAX RpdRemotePortInfomationEntry
			ACCESS not-accessible
			STATUS mandatory
			INDEX { rpdRemotePortInfomationIndex }
			::= { rpdRemotePortInfomationTable 1 }

		
		RpdRemotePortInfomationEntry ::=
			SEQUENCE { 
				rpdRemotePortInfomationIndex
					INTEGER,
				rpdRemotePortInformationStatus
					INTEGER,
				rpdRemotePortInfomationBitrate
					INTEGER,
				rpdRemotePortInfomationWaveLength
					INTEGER,
				rpdRemotePortInfomationTemperature
					INTEGER,
				rpdRemotePortInfomationMacAddress
					TPhysAddress
			 }

		-- 1.3.6.1.4.1.3715.100.103.5.2.1.1
		rpdRemotePortInfomationIndex OBJECT-TYPE
			SYNTAX INTEGER (1..3)
			ACCESS read-write
			STATUS mandatory
			::= { rpdRemotePortInfomationEntry 1 }

		
		-- 1.3.6.1.4.1.3715.100.103.5.2.1.2
		rpdRemotePortInformationStatus OBJECT-TYPE
			SYNTAX INTEGER
			ACCESS read-only
			STATUS mandatory
			DESCRIPTION
				"Remote port (SFP) status.
				
				1: link up, 
				2: link down, 
				3: error, 
				4: unknown, 
				5: N/A, 
				6: no SFP, 
				7: no fiber"
			::= { rpdRemotePortInfomationEntry 2 }

		
		-- 1.3.6.1.4.1.3715.100.103.5.2.1.3
		rpdRemotePortInfomationBitrate OBJECT-TYPE
			SYNTAX INTEGER
			ACCESS read-only
			STATUS mandatory
			DESCRIPTION
				"Remote port (SFP) bitrate. Unit 1 Mbps.
				
				0: Bitrate info not available."
			::= { rpdRemotePortInfomationEntry 3 }

		
		-- 1.3.6.1.4.1.3715.100.103.5.2.1.4
		rpdRemotePortInfomationWaveLength OBJECT-TYPE
			SYNTAX INTEGER
			ACCESS read-only
			STATUS mandatory
			DESCRIPTION
				"Remote port (SFP) wavelength. Unit 0.001 nm. 
				
				Example: 
				1310456 means: 1310.456 nm."
			::= { rpdRemotePortInfomationEntry 4 }

		
		-- 1.3.6.1.4.1.3715.100.103.5.2.1.5
		rpdRemotePortInfomationTemperature OBJECT-TYPE
			SYNTAX INTEGER
			ACCESS read-only
			STATUS mandatory
			DESCRIPTION
				"Remote port (SFP) temperature. Unit 0.01 oC.
				Exact value 0.00 oC (0x0000) indicates that temperature information is not available."
			::= { rpdRemotePortInfomationEntry 5 }

		
		-- 1.3.6.1.4.1.3715.100.103.5.2.1.6
		rpdRemotePortInfomationMacAddress OBJECT-TYPE
			SYNTAX TPhysAddress
			ACCESS read-only
			STATUS mandatory
			DESCRIPTION
				"Remote maangement port (SFP) MAC address. 
				If the MAC address is unknown '00.00.00.00.00.00' is returned."
			::= { rpdRemotePortInfomationEntry 6 }

		
		-- 1.3.6.1.4.1.3715.100.103.6
		rpdDsChannels OBJECT IDENTIFIER ::= { rpd 6 }

		
		-- 1.3.6.1.4.1.3715.100.103.6.1
		rpdNumberOfDownStreams OBJECT-TYPE
			SYNTAX INTEGER
			ACCESS read-only
			STATUS mandatory
			DESCRIPTION
				"Number of down streams (DS). Unit 1 DS."
			::= { rpdDsChannels 1 }

		
		-- 1.3.6.1.4.1.3715.100.103.6.2
		rpdDsChannelsTable OBJECT-TYPE
			SYNTAX SEQUENCE OF RpdDsChannelsEntry
			ACCESS not-accessible
			STATUS mandatory
			::= { rpdDsChannels 2 }

		
		-- 1.3.6.1.4.1.3715.100.103.6.2.1
		rpdDsChannelsEntry OBJECT-TYPE
			SYNTAX RpdDsChannelsEntry
			ACCESS not-accessible
			STATUS mandatory
			INDEX { rpdDsChannelsTableIndex }
			::= { rpdDsChannelsTable 1 }

		
		RpdDsChannelsEntry ::=
			SEQUENCE { 
				rpdDsChannelsTableIndex
					INTEGER,
				rpdDsChannelsTableData0-399
					OCTET STRING,
				rpdDsChannelsTableData400-799
					OCTET STRING,
				rpdDsChannelsTableData800-1199
					OCTET STRING,
				rpdDsChannelsTableData1200-1599
					OCTET STRING,
				rpdDsChannelsTableData1600-1999
					OCTET STRING,
				rpdDsChannelsNumberOfChannels
					INTEGER
			 }

		-- 1.3.6.1.4.1.3715.100.103.6.2.1.1
		rpdDsChannelsTableIndex OBJECT-TYPE
			SYNTAX INTEGER (1..4)
			ACCESS read-write
			STATUS mandatory
			::= { rpdDsChannelsEntry 1 }

		
		-- 1.3.6.1.4.1.3715.100.103.6.2.1.2
		rpdDsChannelsTableData0-399 OBJECT-TYPE
			SYNTAX OCTET STRING
			ACCESS read-only
			STATUS mandatory
			DESCRIPTION
				"Bytecoded data.
				
				Type: uint8:
				- 0: Type 0 is used to indicate uninitialized channel table data. Stop processing channel entries. No valid data after this for this table/block.
				- 1: This whole channel info is not used; no need to check this table/block further.
				- 2: Unused/fill, skip to next ChannelInfoEntry.
				- 3: N/A
				- 4: Analog
				- 5: AM
				- 6: FM
				- 7: PM
				- 8: ASK
				- 9: FSK
				- 10: PSK
				- 11: OOK
				- 12: CW
				- 13: Pilot
				- 14: RPG pilot
				- 15: Optical transmitter pilot
				- 16: HMS MAC
				- 17: CATVisor MAC
				- 18: RIS MAC
				- 19: PAL
				- 20: SECAM
				- 21: NTSC
				- 22: NDF
				- 23: NDR
				- 24: OOB
				- 25: QPSK
				- 26: AnnexA - modulation order unknown
				- 27: AnnexA - QAM2
				- 28: AnnexA - QAM4
				- 29: AnnexA - QAM8
				- 30: AnnexA - QAM16
				- 31: AnnexA - QAM32
				- 32: AnnexA - QAM64
				- 33: AnnexA - QAM128
				- 34: AnnexA - QAM256
				- 35: AnnexA - QAM512
				- 36: AnnexA - QAM1024
				- 37: AnnexA - QAM2048
				- 38: AnnexA - QAM4096
				- 39: AnnexA - QAM8192
				- 40: AnnexA - QAM16384
				- 41: AnnexA - QAM32768
				- 42: AnnexA - QAM65536
				- 43: AnnexA - QAM131072
				- 44: AnnexB - modulation order unknown
				- 45: AnnexB - QAM2
				- 46: AnnexB - QAM4
				- 47: AnnexB - QAM8
				- 48: AnnexB - QAM16
				- 49: AnnexB - QAM32
				- 50: AnnexB - QAM64
				- 51: AnnexB - QAM128
				- 52: AnnexB - QAM256
				- 53: AnnexB - QAM512
				- 54: AnnexB - QAM1024
				- 55: AnnexB - QAM2048
				- 56: AnnexB - QAM4096
				- 57: AnnexB - QAM8192
				- 58: AnnexB - QAM16384
				- 59: AnnexB - QAM32768
				- 60: AnnexB - QAM65536
				- 61: AnnexB - QAM131072
				- 62: AnnexC - modulation order unknown
				- 63: AnnexC - QAM2
				- 64: AnnexC - QAM4
				- 65: AnnexC - QAM8
				- 66: AnnexC - QAM16
				- 67: AnnexC - QAM32
				- 68: AnnexC - QAM64
				- 69: AnnexC - QAM128
				- 70: AnnexC - QAM256
				- 71: AnnexC - QAM512
				- 72: AnnexC - QAM1024
				- 73: AnnexC - QAM2048
				- 74: AnnexC - QAM4096
				- 75: AnnexC - QAM8192
				- 76: AnnexC - QAM16384
				- 77: AnnexC - QAM32768
				- 78: AnnexC - QAM65536
				- 79: AnnexC - QAM131072
				- 80: OFDM (full channel/contiguous channel)
				- 81: OFDM (start of channel)
				- 82: OFDM (continued channel)
				- 83: OFDM (continued channel and end of channel)
				- 84: OFDMA (full channel/contiguous channel)
				- 85: OFDMA (start of channel)
				- 86: OFDMA (continued channel)
				- 87: OFDMA (continued channel and end of channel)
				- 88: Ingress
				- 89: Noise
				- 90: White noise
				- 91: Test signal
				- 92: Viavi signal
				- 93: Other
				- 94: Other downstream
				- 95: Other upstream
				- 96: Unknown
				- 97: Unknown dowstream
				- 98: Unknown upstream
				- 99: No channels at all. This is used when there's no RF channels, but automatic powersave is in use and there's need to get hybrid bias to minimum.
				Status: uint8: bitwise coded
				- 0x01	Status ok
				- 0x02	No cable modems online
				- 0x04	Cable modem(s) registering
				- 0x08	Cable modem(s) registered, no traffic
				- 0x10	Cable modem(s) registered, traffic/transmitting data
				- 0x20	reserved
				- 0x40	Not used channel (used to fill channel info table)
				- 0x80	EndOfChannels
				Start frequency: uint16	
				- Unit&scale	0,05 MHz
				- Range	0...3276,75 MHz
				Stop frequency: uint16	
				- Unit&scale	0,05 MHz
				- Range	0...3276,75 MHz
				Level: int16	
				- Unit&scale	0,01 dBmV/1 MHz channel
				- Range	-327,68...327,67 dBmV
				Slope: int8	
				- Unit&scale	0,2 dB
				- Range	-25,6...25,4 dB
				SNR: uint8	
				- Unit&scale	0,2 dB
				- Range	0...51,0 dB
				
				
				
				"
			::= { rpdDsChannelsEntry 2 }

		
		-- 1.3.6.1.4.1.3715.100.103.6.2.1.3
		rpdDsChannelsTableData400-799 OBJECT-TYPE
			SYNTAX OCTET STRING
			ACCESS read-only
			STATUS mandatory
			DESCRIPTION
				"Bytecoded data.
				
				Description: See rpdDsChannelsTableData0-399."
			::= { rpdDsChannelsEntry 3 }

		
		-- 1.3.6.1.4.1.3715.100.103.6.2.1.4
		rpdDsChannelsTableData800-1199 OBJECT-TYPE
			SYNTAX OCTET STRING
			ACCESS read-only
			STATUS mandatory
			DESCRIPTION
				"Bytecoded data.
				
				Description: See rpdDsChannelsTableData0-399."
			::= { rpdDsChannelsEntry 4 }

		
		-- 1.3.6.1.4.1.3715.100.103.6.2.1.5
		rpdDsChannelsTableData1200-1599 OBJECT-TYPE
			SYNTAX OCTET STRING
			ACCESS read-only
			STATUS mandatory
			DESCRIPTION
				"Bytecoded data.
				
				Description: See rpdDsChannelsTableData0-399."
			::= { rpdDsChannelsEntry 5 }

		
		-- 1.3.6.1.4.1.3715.100.103.6.2.1.6
		rpdDsChannelsTableData1600-1999 OBJECT-TYPE
			SYNTAX OCTET STRING
			ACCESS read-only
			STATUS mandatory
			DESCRIPTION
				"Bytecoded data.
				
				Description: See rpdDsChannelsTableData0-399."
			::= { rpdDsChannelsEntry 6 }
-- 
-- 
		
		-- 1.3.6.1.4.1.3715.100.103.6.2.1.7
		rpdDsChannelsNumberOfChannels OBJECT-TYPE
			SYNTAX INTEGER (0..200)
			ACCESS read-only
			STATUS mandatory
			DESCRIPTION
				"Number of channels in rpdDsChannelsTableData."
			::= { rpdDsChannelsEntry 7 }

		
		-- 1.3.6.1.4.1.3715.100.103.7
		rpdUsChannels OBJECT IDENTIFIER ::= { rpd 7 }

		
		-- 1.3.6.1.4.1.3715.100.103.7.1
		rpdNumberOfUpStreams OBJECT-TYPE
			SYNTAX INTEGER
			ACCESS read-only
			STATUS mandatory
			DESCRIPTION
				"Number of up streams (US). Unit 1 US."
			::= { rpdUsChannels 1 }

		
		-- 1.3.6.1.4.1.3715.100.103.7.2
		rpdUsChannelsTable OBJECT-TYPE
			SYNTAX SEQUENCE OF RpdUsChannelsEntry
			ACCESS not-accessible
			STATUS mandatory
			::= { rpdUsChannels 2 }

		
		-- 1.3.6.1.4.1.3715.100.103.7.2.1
		rpdUsChannelsEntry OBJECT-TYPE
			SYNTAX RpdUsChannelsEntry
			ACCESS not-accessible
			STATUS mandatory
			INDEX { rpdUsChannelsTableIndex }
			::= { rpdUsChannelsTable 1 }

		
		RpdUsChannelsEntry ::=
			SEQUENCE { 
				rpdUsChannelsTableIndex
					INTEGER,
				rpdUsChannelsTableData0-399
					OCTET STRING,
				rpdUsChannelsTableData400-799
					OCTET STRING,
				rpdUsChannelsTableData800-1199
					OCTET STRING,
				rpdUsChannelsTableData1200-1599
					OCTET STRING,
				rpdUsChannelsTableData1600-1999
					OCTET STRING,
				rpdUsChannelsNumberOfChannels
					INTEGER
			 }

		-- 1.3.6.1.4.1.3715.100.103.7.2.1.1
		rpdUsChannelsTableIndex OBJECT-TYPE
			SYNTAX INTEGER (1..4)
			ACCESS read-write
			STATUS mandatory
			::= { rpdUsChannelsEntry 1 }

		
		-- 1.3.6.1.4.1.3715.100.103.7.2.1.2
		rpdUsChannelsTableData0-399 OBJECT-TYPE
			SYNTAX OCTET STRING
			ACCESS read-only
			STATUS mandatory
			DESCRIPTION
				"Bytecoded data.
				
				Description: See rpdDsChannelsTableData0-399."
			::= { rpdUsChannelsEntry 2 }
-- 
-- 
-- 
-- 
		
		-- 1.3.6.1.4.1.3715.100.103.7.2.1.3
		rpdUsChannelsTableData400-799 OBJECT-TYPE
			SYNTAX OCTET STRING
			ACCESS read-only
			STATUS mandatory
			DESCRIPTION
				"Bytecoded data.
				
				Description: See rpdDsChannelsTableData0-399."
			::= { rpdUsChannelsEntry 3 }

		
		-- 1.3.6.1.4.1.3715.100.103.7.2.1.4
		rpdUsChannelsTableData800-1199 OBJECT-TYPE
			SYNTAX OCTET STRING
			ACCESS read-only
			STATUS mandatory
			DESCRIPTION
				"Bytecoded data.
				
				Description: See rpdDsChannelsTableData0-399."
			::= { rpdUsChannelsEntry 4 }

		
		-- 1.3.6.1.4.1.3715.100.103.7.2.1.5
		rpdUsChannelsTableData1200-1599 OBJECT-TYPE
			SYNTAX OCTET STRING
			ACCESS read-only
			STATUS mandatory
			DESCRIPTION
				"Bytecoded data.
				
				Description: See rpdDsChannelsTableData0-399."
			::= { rpdUsChannelsEntry 5 }

		
		-- 1.3.6.1.4.1.3715.100.103.7.2.1.6
		rpdUsChannelsTableData1600-1999 OBJECT-TYPE
			SYNTAX OCTET STRING
			ACCESS read-only
			STATUS mandatory
			DESCRIPTION
				"Bytecoded data.
				
				Description: See rpdUsChannelsTableData0-399."
			::= { rpdUsChannelsEntry 6 }
-- 
-- 
		
		-- 1.3.6.1.4.1.3715.100.103.7.2.1.7
		rpdUsChannelsNumberOfChannels OBJECT-TYPE
			SYNTAX INTEGER (0..200)
			ACCESS read-only
			STATUS mandatory
			DESCRIPTION
				"Number of channels in rpdUsChannelsTableData."
			::= { rpdUsChannelsEntry 7 }

		
		-- 1.3.6.1.4.1.3715.100.103.8
		rpdStatusLog OBJECT IDENTIFIER ::= { rpd 8 }

		
		-- 1.3.6.1.4.1.3715.100.103.8.1
		rpdStatusLogRowCount OBJECT-TYPE
			SYNTAX INTEGER
			ACCESS read-only
			STATUS mandatory
			DESCRIPTION
				"Number of rows in status log."
			::= { rpdStatusLog 1 }

		
		-- 1.3.6.1.4.1.3715.100.103.8.2
		rpdStatusLogLastIndex OBJECT-TYPE
			SYNTAX INTEGER (1..65535)
			ACCESS read-only
			STATUS mandatory
			DESCRIPTION
				"Last log index."
			::= { rpdStatusLog 2 }

		
		-- 1.3.6.1.4.1.3715.100.103.8.3
		rpdStatusLogTable OBJECT-TYPE
			SYNTAX SEQUENCE OF RpdStatusLogEntry
			ACCESS not-accessible
			STATUS mandatory
			::= { rpdStatusLog 3 }

		
		-- 1.3.6.1.4.1.3715.100.103.8.3.1
		rpdStatusLogEntry OBJECT-TYPE
			SYNTAX RpdStatusLogEntry
			ACCESS not-accessible
			STATUS mandatory
			INDEX { rpdStatusLogStorageSlot }
			::= { rpdStatusLogTable 1 }

		
		RpdStatusLogEntry ::=
			SEQUENCE { 
				rpdStatusLogStorageSlot
					INTEGER,
				rpdStatusLogIndex
					INTEGER,
				rpdStatusLogTimeStamp
					OCTET STRING,
				rpdStatusLogText
					OCTET STRING
			 }

		-- 1.3.6.1.4.1.3715.100.103.8.3.1.1
		rpdStatusLogStorageSlot OBJECT-TYPE
			SYNTAX INTEGER (1..65535)
			ACCESS read-write
			STATUS mandatory
			DESCRIPTION
				"Status log event storage slot.
				Device has limited (and fixed number of) storage slots. Events are returned on storage slot order. To get correct chronological order, 
				sort entries using rpdStatusLogIndex (taking care of index wrap around)."
			::= { rpdStatusLogEntry 1 }

		
		-- 1.3.6.1.4.1.3715.100.103.8.3.1.2
		rpdStatusLogIndex OBJECT-TYPE
			SYNTAX INTEGER (1..65535)
			ACCESS read-write
			STATUS mandatory
			DESCRIPTION
				"Index of log entry. Wraps around.
				Log entries are returned in storage slot order.
				This field indicates chronological order.
				
				If rpdStatusLogIndex value is 0, then this storage slot is uninitialized and does not contain any relevant information."
			::= { rpdStatusLogEntry 2 }

		
		-- 1.3.6.1.4.1.3715.100.103.8.3.1.3
		rpdStatusLogTimeStamp OBJECT-TYPE
			SYNTAX OCTET STRING
			ACCESS read-only
			STATUS mandatory
			DESCRIPTION
				"Timestamp of event.
				
				If rpdStatusLogTimeStamp value is 0, then this storage slot is uninitialized and does not contain any relevant information."
			::= { rpdStatusLogEntry 3 }

		
		-- 1.3.6.1.4.1.3715.100.103.8.3.1.4
		rpdStatusLogText OBJECT-TYPE
			SYNTAX OCTET STRING (SIZE (0..50))
			ACCESS read-only
			STATUS mandatory
			DESCRIPTION
				"Textual description of event. Field maximum size uint8[50]."
			::= { rpdStatusLogEntry 4 }

		
		-- 1.3.6.1.4.1.3715.100.103.9
		rpdNodeInfo OBJECT IDENTIFIER ::= { rpd 9 }

		
		-- 1.3.6.1.4.1.3715.100.103.9.1
		rpdNodeOutputPower1 OBJECT-TYPE
			SYNTAX INTEGER
			ACCESS read-only
			STATUS mandatory
			DESCRIPTION
				"Output 1 power calculated from appropriate DS channel table (based on routing) and gain&slope settings by node.
				If no channel info available, value 9999 is returned. 
				If output is not in use -9999 is returned.
				
				Unit 0.01 dBm"
			::= { rpdNodeInfo 1 }

		
		-- 1.3.6.1.4.1.3715.100.103.9.2
		rpdNodeOutputPower2 OBJECT-TYPE
			SYNTAX INTEGER
			ACCESS read-only
			STATUS mandatory
			DESCRIPTION
				"Output 2 power calculated from appropriate DS channel table (based on routing) and gain&slope settings by node.
				If no channel info available, value 9999 is returned. 
				If output is not in use -9999 is returned.
				
				Unit 0.01 dBm"
			::= { rpdNodeInfo 2 }

		
		-- 1.3.6.1.4.1.3715.100.103.9.3
		rpdNodeOutputPower3 OBJECT-TYPE
			SYNTAX INTEGER
			ACCESS read-only
			STATUS mandatory
			DESCRIPTION
				"Output 3 power calculated from appropriate DS channel table (based on routing) and gain&slope settings by node.
				If no channel info available, value 9999 is returned. 
				If output is not in use -9999 is returned.
				
				Unit 0.01 dBm"
			::= { rpdNodeInfo 3 }

		
		-- 1.3.6.1.4.1.3715.100.103.9.4
		rpdNodeOutputPower4 OBJECT-TYPE
			SYNTAX INTEGER
			ACCESS read-only
			STATUS mandatory
			DESCRIPTION
				"Output 1 power calculated from appropriate DS channel table (based on routing) and gain&slope settings by node.
				If no channel info available, value 9999 is returned. 
				If output is not in use -9999 is returned.
				
				Unit 0.01 dBm"
			::= { rpdNodeInfo 4 }

		
		-- 1.3.6.1.4.1.3715.100.103.10
		rpdUps OBJECT IDENTIFIER ::= { rpd 10 }

		
		-- 1.3.6.1.4.1.3715.100.103.10.1
		upsStatus OBJECT-TYPE
			SYNTAX INTEGER
				{
				upsStatusOk(1),
				upsStatusActive(2),
				upsStatusFailure(3),
				upsStatusNA(4)
				}
			ACCESS read-only
			STATUS mandatory
			DESCRIPTION
				"UPS status.
				1: Normal operation, everything ok.
				2: UPS activated.
				3: UPS failure. Internal error in UPS.
				4: UPS not available."
			::= { rpdUps 1 }

		
		-- 1.3.6.1.4.1.3715.100.103.10.2
		upsCounterReset OBJECT-TYPE
			SYNTAX INTEGER
			ACCESS read-write
			STATUS mandatory
			DESCRIPTION
				"UPS reset requests. Bitfield
				- 0x0001: Request UPS to do SwReset
				- 0x0010: Request UPS to clear log
				- 0x0020: Request UPS to clear activation/failed/successful counter
				- 0x0080: Request UPS to clear charging started/charging interrupted/charging finished counter
				
				Read returns always 0."
			::= { rpdUps 2 }

		
		-- 1.3.6.1.4.1.3715.100.103.10.3
		upsIdData OBJECT-TYPE
			SYNTAX OCTET STRING
			ACCESS read-only
			STATUS mandatory
			DESCRIPTION
				"UPS Identification data (32 bytes). Unused chars are set to 0x00 (so C string, not pascal string)
				'- Serial number: char [10]; e.g. SK20201208
				'- Type/Model: char[15]; e.g. UPS123
				'- HwVersion: char[4]; e.g. A1.0
				'- Driver: uint8_t; e.g. 0xFD
				'- Fletcher checkum: uint16_t"
			::= { rpdUps 3 }

		
		-- 1.3.6.1.4.1.3715.100.103.10.4
		upsStatusData OBJECT-TYPE
			SYNTAX OCTET STRING
			ACCESS read-only
			STATUS mandatory
			DESCRIPTION
				"UPS status
				- Current posix time: uint32_t [1 s]
				- Current uptime (full days): uint32_t [1 d]
				- Current uptime (seconds in this day): uint32_t [1 s]
				- Total uptime (full days): uint32_t [1 d]
				- Reset count: uint32_t [1 reset]
				- Maximum Event log entry count (MaximumEventLogEntryCount): uint32_t [1]
				- Application version (vMAJOR.MINOR.BUILD): uint32_t: 0xMAMIBUIL, where MA: major (uint8_t), MI: minor (uint8_t), BUIL: build (uint16_t)
				- Application build date: uint32_t: 0xDDMMYYYY, where DD: Application build day (uint8_t; 1-31), MM: Application build month (uint8_t; 1-12), YYYY: Application build year (uint16_t; 0-65535)
				- Current temperature: int32_t [0.01 oC]; if temperature not available, return -99999.
				- Last UPS activation time (posix time stamp): uint32_t [1 s]; if UPS has not been active: 0.
				- Seconds since last UPS activation: uint32_t [1 s]; if UPS has not been active: 0.
				- UPS activation count: uint32_t [1 activation]; end user can reset this.
				- UPS total activation count: uint32_t [1]; this this not end-user resetable.
				- UPS failed count: uint32_t [1]; end user can reset this.
				- UPS total failed count: uint32_t [1]; this this not end-user resetable.
				- UPS successful count: uint32_t [1 activation]; end user can reset this.
				- UPS total successful count: uint32_t [1 activation]; this this not end-user resetable.
				- UPS charging started count: uint32_t [1 activation]; end user can reset this.
				- UPS total charging started count: uint32_t [1 activation]; this this not end-user resetable.
				- UPS charging finished count: uint32_t [1 activation]; end user can reset this.
				- UPS total charging finished count: uint32_t [1 activation]; this this not end-user resetable.
				- UPS charging interrupted count: uint32_t [1 activation]; end user can reset this.
				- UPS total charging interrupted count: uint32_t [1 activation]; this this not end-user resetable."
			::= { rpdUps 4 }

		
		-- 1.3.6.1.4.1.3715.100.103.10.5
		upsTemperatureHistogram OBJECT-TYPE
			SYNTAX OCTET STRING
			ACCESS read-only
			STATUS mandatory
			DESCRIPTION
				"Temperature histogram data.
				- uint16 Number of temperature measurements < 5 oC
				- uint16 Number of temperature measurements 5…15 oC
				- uint16 Number of temperature measurements 15…25 oC
				- uint16 Number of temperature measurements 25…35 oC
				- uint16 Number of temperature measurements 35…45 oC
				- uint16 Number of temperature measurements 45…55 oC
				- uint16 Number of temperature measurements 55…65 oC
				- uint16 Number of temperature measurements 65…75 oC
				- uint16 Number of temperature measurements 75…85 oC
				- uint16 Number of temperature measurements > 85 oC
				"
			::= { rpdUps 5 }

		
		-- 1.3.6.1.4.1.3715.100.103.11
		rpdUpsEventLog OBJECT IDENTIFIER ::= { rpd 11 }

		
		-- 1.3.6.1.4.1.3715.100.103.11.1
		rpdUpsEventLogRowCount OBJECT-TYPE
			SYNTAX INTEGER
			ACCESS read-only
			STATUS mandatory
			DESCRIPTION
				"Number of rows in UPS event log."
			::= { rpdUpsEventLog 1 }

		
		-- 1.3.6.1.4.1.3715.100.103.11.2
		rpdUpsEventLogTable OBJECT-TYPE
			SYNTAX SEQUENCE OF RpdUpsEventLogEntry
			ACCESS not-accessible
			STATUS mandatory
			::= { rpdUpsEventLog 2 }

		
		-- 1.3.6.1.4.1.3715.100.103.11.2.1
		rpdUpsEventLogEntry OBJECT-TYPE
			SYNTAX RpdUpsEventLogEntry
			ACCESS not-accessible
			STATUS mandatory
			INDEX { rpdUpsEventLogStorageSlot }
			::= { rpdUpsEventLogTable 1 }

		
		RpdUpsEventLogEntry ::=
			SEQUENCE { 
				rpdUpsEventLogStorageSlot
					INTEGER,
				rpdUpsEventLogData
					OCTET STRING
			 }

		-- 1.3.6.1.4.1.3715.100.103.11.2.1.1
		rpdUpsEventLogStorageSlot OBJECT-TYPE
			SYNTAX INTEGER (1..1000)
			ACCESS read-only
			STATUS mandatory
			DESCRIPTION
				"UPS event log storage slot.
				Device has limited (and fixed number of) storage slots. Events are returned on storage slot order. To get correct chronological order, 
				sort entries using rpdUpsEventLogData.EventIndex (taking care of index wrap around)."
			::= { rpdUpsEventLogEntry 1 }

		
		-- 1.3.6.1.4.1.3715.100.103.11.2.1.2
		rpdUpsEventLogData OBJECT-TYPE
			SYNTAX OCTET STRING
			ACCESS read-only
			STATUS mandatory
			DESCRIPTION
				"UPS event log entry
				- Index of event (IndexOfEvent): uint32_t (range: 1...2^32-1)
				- EventTime (= posix timestamp): uint32_t
				- Reset count @ event time: uint32_t
				- EventType: uint32_t
				- EventInfo: uint32_t"
			::= { rpdUpsEventLogEntry 2 }

		
		-- 1.3.6.1.4.1.3715.100.103.12
		rpdShelfPsu OBJECT IDENTIFIER ::= { rpd 12 }

		
		-- 1.3.6.1.4.1.3715.100.103.12.1
		rpdShelfPsuNumberOfPsus OBJECT-TYPE
			SYNTAX INTEGER
			ACCESS read-only
			STATUS mandatory
			DESCRIPTION
				"Number of PSUs."
			::= { rpdShelfPsu 1 }

		
		-- 1.3.6.1.4.1.3715.100.103.12.2
		rpdShelfPsuTable OBJECT-TYPE
			SYNTAX SEQUENCE OF RpdShelfPsuEntry
			ACCESS not-accessible
			STATUS mandatory
			::= { rpdShelfPsu 2 }

		
		-- 1.3.6.1.4.1.3715.100.103.12.2.1
		rpdShelfPsuEntry OBJECT-TYPE
			SYNTAX RpdShelfPsuEntry
			ACCESS not-accessible
			STATUS mandatory
			INDEX { rpdShelfPsuIndex }
			::= { rpdShelfPsuTable 1 }

		
		RpdShelfPsuEntry ::=
			SEQUENCE { 
				rpdShelfPsuIndex
					INTEGER,
				rpdShelfPsuHwModel
					OCTET STRING,
				rpdShelfPsuSerialNumber
					OCTET STRING,
				rpdShelfPsuHwVersion
					OCTET STRING,
				rpdShelfPsuSwVersion
					OCTET STRING,
				rpdShelfPsuInstallationPosition
					INTEGER,
				rpdShelfPsuUptime
					OCTET STRING,
				rpdShelfPsuTotalUptime
					INTEGER,
				rpdShelfPsuResetCount
					INTEGER,
				rpdShelfPsu24Voltage
					INTEGER,
				rpdShelfPsuCurrent
					INTEGER,
				rpdShelfPsuTemperature
					INTEGER,
				rpdShelfPsuFan1rpm
					INTEGER,
				rpdShelfPsuFan2rpm
					INTEGER,
				rpdShelfPsuFan1Status
					INTEGER,
				rpdShelfPsuFan2Status
					INTEGER,
				rpdShelfPsuFailureBits
					INTEGER
			 }

		-- 1.3.6.1.4.1.3715.100.103.12.2.1.1
		rpdShelfPsuIndex OBJECT-TYPE
			SYNTAX INTEGER (1..10)
			ACCESS read-only
			STATUS mandatory
			DESCRIPTION
				"Index of PSU."
			::= { rpdShelfPsuEntry 1 }

		
		-- 1.3.6.1.4.1.3715.100.103.12.2.1.2
		rpdShelfPsuHwModel OBJECT-TYPE
			SYNTAX OCTET STRING
			ACCESS read-only
			STATUS mandatory
			DESCRIPTION
				"Hardware model of PSU.
				If hardware model is undefined, then zero length string is returned."
			::= { rpdShelfPsuEntry 2 }

		
		-- 1.3.6.1.4.1.3715.100.103.12.2.1.3
		rpdShelfPsuSerialNumber OBJECT-TYPE
			SYNTAX OCTET STRING
			ACCESS read-only
			STATUS mandatory
			DESCRIPTION
				"Serial number of PSU.
				If serial number is undefined, then zero length string is returned."
			::= { rpdShelfPsuEntry 3 }

		
		-- 1.3.6.1.4.1.3715.100.103.12.2.1.4
		rpdShelfPsuHwVersion OBJECT-TYPE
			SYNTAX OCTET STRING
			ACCESS read-only
			STATUS mandatory
			DESCRIPTION
				"Hardware version of PSU.
				If hardware version is undefined, then zero length string is returned."
			::= { rpdShelfPsuEntry 4 }

		
		-- 1.3.6.1.4.1.3715.100.103.12.2.1.5
		rpdShelfPsuSwVersion OBJECT-TYPE
			SYNTAX OCTET STRING
			ACCESS read-only
			STATUS mandatory
			DESCRIPTION
				"Software version information.
				This might contain only application version number, but is not limited to that. It might contain information about BIOS and dates.
				If software version is undefined, then zero length string is returned."
			::= { rpdShelfPsuEntry 5 }

		
		-- 1.3.6.1.4.1.3715.100.103.12.2.1.6
		rpdShelfPsuInstallationPosition OBJECT-TYPE
			SYNTAX INTEGER
				{
				rpdShelfPsuInstallationPositionNA(1),
				rpdShelfPsuInstallationPositionUnknown(2),
				rpdShelfPsuInstallationPositionA(3),
				rpdShelfPsuInstallationPositionB(4)
				}
			ACCESS read-only
			STATUS mandatory
			DESCRIPTION
				"PSU installation position in rack.
				1: N/A
				2: Unknown
				3: A (left)
				4: B (right)
				"
			::= { rpdShelfPsuEntry 6 }

		
		-- 1.3.6.1.4.1.3715.100.103.12.2.1.7
		rpdShelfPsuUptime OBJECT-TYPE
			SYNTAX OCTET STRING
			ACCESS read-only
			STATUS mandatory
			DESCRIPTION
				"Current uptime of PSU."
			::= { rpdShelfPsuEntry 7 }

		
		-- 1.3.6.1.4.1.3715.100.103.12.2.1.8
		rpdShelfPsuTotalUptime OBJECT-TYPE
			SYNTAX INTEGER
			ACCESS read-only
			STATUS mandatory
			DESCRIPTION
				"Total uptime the PSU (software) has been running.
				Unit 1 day."
			::= { rpdShelfPsuEntry 8 }

		
		-- 1.3.6.1.4.1.3715.100.103.12.2.1.9
		rpdShelfPsuResetCount OBJECT-TYPE
			SYNTAX INTEGER
			ACCESS read-only
			STATUS mandatory
			DESCRIPTION
				"Total number of software resets during PSU's life time.
				Unit 1 reset."
			::= { rpdShelfPsuEntry 9 }

		
		-- 1.3.6.1.4.1.3715.100.103.12.2.1.10
		rpdShelfPsu24Voltage OBJECT-TYPE
			SYNTAX INTEGER
			ACCESS read-only
			STATUS mandatory
			DESCRIPTION
				"+24 Vdc voltage measured by PSU.
				Unit 0.01 V."
			::= { rpdShelfPsuEntry 10 }

		
		-- 1.3.6.1.4.1.3715.100.103.12.2.1.11
		rpdShelfPsuCurrent OBJECT-TYPE
			SYNTAX INTEGER
			ACCESS read-only
			STATUS mandatory
			DESCRIPTION
				"Current measured by PSU.
				Unit 0.01 A."
			::= { rpdShelfPsuEntry 11 }

		
		-- 1.3.6.1.4.1.3715.100.103.12.2.1.12
		rpdShelfPsuTemperature OBJECT-TYPE
			SYNTAX INTEGER
			ACCESS read-only
			STATUS mandatory
			DESCRIPTION
				"Temperature measured by PSU.
				Unit 0.01 oC."
			::= { rpdShelfPsuEntry 12 }

		
		-- 1.3.6.1.4.1.3715.100.103.12.2.1.13
		rpdShelfPsuFan1rpm OBJECT-TYPE
			SYNTAX INTEGER
			ACCESS read-only
			STATUS mandatory
			DESCRIPTION
				"PSU's fan 1 rpm's measured by PSU.
				Unit 1 rpm."
			::= { rpdShelfPsuEntry 13 }

		
		-- 1.3.6.1.4.1.3715.100.103.12.2.1.14
		rpdShelfPsuFan2rpm OBJECT-TYPE
			SYNTAX INTEGER
			ACCESS read-only
			STATUS mandatory
			DESCRIPTION
				"PSU's fan 2 rpm's measured by PSU.
				Unit 1 rpm."
			::= { rpdShelfPsuEntry 14 }

		
		-- 1.3.6.1.4.1.3715.100.103.12.2.1.15
		rpdShelfPsuFan1Status OBJECT-TYPE
			SYNTAX INTEGER
				{
				rpdShelfPsuFan1StatusOk(1),
				rpdShelfPsuFan1StatusFailure(2),
				rpdShelfPsuFan1StatusNA(3)
				}
			ACCESS read-only
			STATUS mandatory
			DESCRIPTION
				"PSU's fan 1 status.
				1: Fan ok
				2: Fan failure
				3: No fan"
			::= { rpdShelfPsuEntry 15 }

		
		-- 1.3.6.1.4.1.3715.100.103.12.2.1.16
		rpdShelfPsuFan2Status OBJECT-TYPE
			SYNTAX INTEGER
				{
				rpdShelfPsuFan2StatusOk(1),
				rpdShelfPsuFan2StatusFailure(2),
				rpdShelfPsuFan2StatusNA(3)
				}
			ACCESS read-only
			STATUS mandatory
			DESCRIPTION
				"PSU's fan 2 status.
				1: Fan ok
				2: Fan failure
				3: No fan"
			::= { rpdShelfPsuEntry 16 }

		
		-- 1.3.6.1.4.1.3715.100.103.12.2.1.17
		rpdShelfPsuFailureBits OBJECT-TYPE
			SYNTAX INTEGER
			ACCESS read-only
			STATUS mandatory
			DESCRIPTION
				"PSU failure bits. If bit is set '1', then failure is active.
				
				0x0001: PSU lost/PSU not detected anymore.
				0x0002: Data communication lost to this PSU.
				0x0004: Data communication lost to other PSU.
				0x0008: PSU +24 V failed.
				0x0010: PSU internal temperature too high.
				0x0020...0x8000: Reserved for future needs."
			::= { rpdShelfPsuEntry 17 }

		
	
	END

--
-- TELESTE-FUNCTIONAL-RPD-MIB.mib
--
