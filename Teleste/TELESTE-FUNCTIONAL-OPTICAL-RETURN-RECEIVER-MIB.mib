--
-- TELESTE-FUNCTIONAL-OPTICAL-RETURN-RECEIVER-MIB.mib
-- MIB generated by MG-SOFT Visual MIB Builder 2013 (64-bit) Version 9.0  Build 760
-- Friday, March 14, 2014 at 09:44:32
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-OPTICAL-RETURN-RECEIVER-MIB
-- 
-- Description:   MIB module describing Teleste functional optical return receiver interface specific objects
-- 
-- Revision history:
-- -----------------
-- 2, 14.3.2014, Sami Kuusisto
-- - Renamed opticalReturnReceiverEnable to opticalReturnReceiverControl.
-- 
-- 1, 12.3.2014, Sami Kuusisto
-- - Initial version.
-- 
-- ****************************************************************************
-- 

	TELESTE-FUNCTIONAL-OPTICAL-RETURN-RECEIVER-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.57
		opticalReturnReceiver OBJECT IDENTIFIER ::= { functional 57 }

		
		-- 1.3.6.1.4.1.3715.100.57.1
		opticalReturnReceiverTable OBJECT-TYPE
			SYNTAX SEQUENCE OF OpticalReturnReceiverEntry
			ACCESS not-accessible
			STATUS mandatory
			DESCRIPTION
				"A table of optical receiver control entries."
			::= { opticalReturnReceiver 1 }

		
		-- 1.3.6.1.4.1.3715.100.57.1.1
		opticalReturnReceiverEntry OBJECT-TYPE
			SYNTAX OpticalReturnReceiverEntry
			ACCESS not-accessible
			STATUS mandatory
			INDEX { functionalModuleId }
			::= { opticalReturnReceiverTable 1 }

		
		OpticalReturnReceiverEntry ::=
			SEQUENCE { 
				opticalReturnReceiverInputPower
					INTEGER,
				opticalReturnReceiverStatus
					INTEGER,
				opticalReturnReceiverControl
					INTEGER,
				opticalReturnReceiverReferenceLevel
					INTEGER
			 }

		-- 1.3.6.1.4.1.3715.100.57.1.1.1
		opticalReturnReceiverInputPower OBJECT-TYPE
			SYNTAX INTEGER
			ACCESS read-only
			STATUS mandatory
			DESCRIPTION
				"Optical input power value. Unit 0.01 dBm.
				This object has an entry in the propertyTable."
			::= { opticalReturnReceiverEntry 1 }

		
		-- 1.3.6.1.4.1.3715.100.57.1.1.2
		opticalReturnReceiverStatus OBJECT-TYPE
			SYNTAX INTEGER
				{
				on(1),
				off(2)
				}
			ACCESS read-only
			STATUS mandatory
			DESCRIPTION
				"Current optical receiver module operating mode:
				1 = receiver ON
				2 = receiver OFF
				"
			::= { opticalReturnReceiverEntry 2 }

		
		-- 1.3.6.1.4.1.3715.100.57.1.1.3
		opticalReturnReceiverControl OBJECT-TYPE
			SYNTAX INTEGER
				{
				rxEnabled(1),
				rxDisabled(2)
				}
			ACCESS read-write
			STATUS mandatory
			DESCRIPTION
				"Optical receiver control:
				1 = receiver is enabled/on
				2 = receiver is disabled/off"
			::= { opticalReturnReceiverEntry 3 }

		
		-- 1.3.6.1.4.1.3715.100.57.1.1.4
		opticalReturnReceiverReferenceLevel OBJECT-TYPE
			SYNTAX INTEGER
			ACCESS read-write
			STATUS mandatory
			DESCRIPTION
				"Optical receiver reference level. Unit 0.01 dBm."
			::= { opticalReturnReceiverEntry 4 }

		
	
	END

--
-- TELESTE-FUNCTIONAL-OPTICAL-RETURN-RECEIVER-MIB.mib
--
