--
-- TELESTE-ANALYSER-MIB.mib
-- MIB generated by MG-SOFT Visual MIB Builder 2018 (64-bit) Version 12.0  Build 1200
-- Wednesday, February 13, 2019 at 10:24:18
--

-- ****************************************************************************
-- Copyright (c) 2008-2010 by:
-- 
-- Teleste Corporation
-- Seponkatu 1
-- FIN-20660 Littoinen, Finland
-- tel. +358 2 2605 611
-- url: http://www.teleste.com
-- 
-- Module Name: TELESTE-ANALYSER-MIB
-- 
-- Description: MIB module for spectrum analyser objects in any Teleste device
-- 
-- Revision History:
-- -----------------
-- 5, 13.2.2019, Sami Kuusisto
-- - Added new enums (minHold(5) and maxHold(6) to spectrumAnalyserChannelTypeByteTable(16).
-- 
-- 4, 1.10.2018, Sami Kuusisto
-- - Changed MIB version numbering scheme.
-- - Added new enums (annexB(3), OFDM(4) and unset(15) to spectrumAnalyserChannelTypeByteTable(16).
-- - Fixed spectrumAnalyserChannelTypeTable(7) description: BITwise encoding, not nibblewise...
-- 
-- 3, 23.3.2016, Sami Kuusisto
-- - Removed lenght/size information from spectrumAnalyserChannelTableName, spectrumAnalyserChannelTable, spectrumAnalyserChannelTypeTable
-- 
-- 2,  31.5.2010, Matti Susi
-- - Changed the descriptions of spectrumAnalyserStatus values
--   and added new value statusHwError
-- 
-- 1,  2.7.2008, Matti Susi
-- - Initial public release
-- 
-- ****************************************************************************
-- 
-- 

	TELESTE-ANALYSER-MIB DEFINITIONS ::= BEGIN
 
		IMPORTS
			OBJECT-TYPE			
				FROM RFC-1212			
			spectrumAnalyser			
				FROM TELESTE-ROOT-MIB;
	
	
--
-- Node definitions
--
	
		-- 1.3.6.1.4.1.3715.100.2.1
		spectrumAnalyserCount OBJECT-TYPE
			SYNTAX INTEGER (0..8)
			ACCESS read-only
			STATUS mandatory
			DESCRIPTION
				"Number of spectrum analysers in this device. Zero value means
				that no analysers are available."
			::= { spectrumAnalyser 1 }

		
		-- 1.3.6.1.4.1.3715.100.2.10
		spectrumAnalyserTable OBJECT-TYPE
			SYNTAX SEQUENCE OF SpectrumAnalyserEntry
			ACCESS not-accessible
			STATUS mandatory
			::= { spectrumAnalyser 10 }

		
		-- 1.3.6.1.4.1.3715.100.2.10.1
		spectrumAnalyserEntry OBJECT-TYPE
			SYNTAX SpectrumAnalyserEntry
			ACCESS not-accessible
			STATUS mandatory
			INDEX { spectrumAnalyserIndex }
			::= { spectrumAnalyserTable 1 }

		
		SpectrumAnalyserEntry ::=
			SEQUENCE { 
				spectrumAnalyserIndex
					INTEGER,
				spectrumAnalyserType
					INTEGER,
				spectrumAnalyserMode
					INTEGER,
				spectrumAnalyserChannelTableName
					OCTET STRING,
				spectrumAnalyserChannelTable
					OCTET STRING,
				spectrumAnalyserChannelTypeTable
					OCTET STRING,
				spectrumAnalyserValueTable
					OCTET STRING,
				spectrumAnalyserHIHILimitTable
					OCTET STRING,
				spectrumAnalyserHiLimitTable
					OCTET STRING,
				spectrumAnalyserLoLimitTable
					OCTET STRING,
				spectrumAnalyserLOLOLimitTable
					OCTET STRING,
				spectrumAnalyserAlarmTolerance
					INTEGER,
				spectrumAnalyserSweepTime
					INTEGER,
				spectrumAnalyserStatus
					INTEGER,
				spectrumAnalyserChannelTypeByteTable
					OCTET STRING
			 }

		-- 1.3.6.1.4.1.3715.100.2.10.1.1
		spectrumAnalyserIndex OBJECT-TYPE
			SYNTAX INTEGER (1..8)
			ACCESS read-only
			STATUS mandatory
			DESCRIPTION
				"Unique index to the analyser table."
			::= { spectrumAnalyserEntry 1 }

		
		-- 1.3.6.1.4.1.3715.100.2.10.1.2
		spectrumAnalyserType OBJECT-TYPE
			SYNTAX INTEGER
				{
				typeForward(1),
				typeReturn(2),
				typeOther(3)
				}
			ACCESS read-only
			STATUS mandatory
			DESCRIPTION
				"Spectrum analyser type:
				1 = typeForward - ACx/HDO type forward path analyser
				2 = typeReturn - ACx type return path analyser
				3 = typeOther - other type of analyser
				
				The analyser value scaling depends on the type.
				
				Value scaling in ACX/HDO type analysers:
				Unit of frequency in spectrumAnalyserChannelTable are is 0.25 MHz
				Unit of level in spectrumAnalyserValueTable and limit tables is 0.5 dB
				"
			::= { spectrumAnalyserEntry 2 }

		
		-- 1.3.6.1.4.1.3715.100.2.10.1.4
		spectrumAnalyserMode OBJECT-TYPE
			SYNTAX INTEGER
				{
				modeOff(1),
				modeOn(2),
				modeRestart(3)
				}
			ACCESS read-write
			STATUS mandatory
			DESCRIPTION
				"Spectrum analyser mode:
				1 = OFF
				2 = ON
				3 = restart scanning"
			::= { spectrumAnalyserEntry 4 }

		
		-- 1.3.6.1.4.1.3715.100.2.10.1.5
		spectrumAnalyserChannelTableName OBJECT-TYPE
			SYNTAX OCTET STRING
			ACCESS read-write
			STATUS mandatory
			DESCRIPTION
				"Name of the channel table file currently in use. 
				
				Length of name is device dependent. See user manual for more information."
			::= { spectrumAnalyserEntry 5 }

		
		-- 1.3.6.1.4.1.3715.100.2.10.1.6
		spectrumAnalyserChannelTable OBJECT-TYPE
			SYNTAX OCTET STRING
			ACCESS read-write
			STATUS mandatory
			DESCRIPTION
				"A string of spectrum analyser measurement frequencies.
				Each octet pair in the string represents one frequency value 
				starting from the lowest frequency.
				
				Value scaling depends on the analyser type. With ACx and HDO
				analysers the unit is 0.25 MHz.
				
				Maximum number of supported frequencies is device dependent. See user manual for more information."
			::= { spectrumAnalyserEntry 6 }

		
		-- 1.3.6.1.4.1.3715.100.2.10.1.7
		spectrumAnalyserChannelTypeTable OBJECT-TYPE
			SYNTAX OCTET STRING
			ACCESS read-write
			STATUS mandatory
			DESCRIPTION
				"A string of spectrum analyser level detector modes. Bitwise encoding, 
				each bit defines the detector mode for the corresponding
				frequency in spectrumAnalyserChannelTable.
				
				Bit values are:
				0 = PAL signal or unmodulated carrier
				1 = QAM (EU)/AnnexA (6.875 MHz) signal
				
				For QAM (US)/AnnexB (5.4 MHz) and OFDM (6.0 MHz), please use spectrumAnalyserChannelTypeByteTable(17) 
				which uses bytewise encoding instead of bitwise encoding.
				If device supports spectrumAnalyserChannelTypeByteTable(17) please use it for all operations and consider
				this object as DEPRECATED.
				 
				Maximum number of supported frequencies is device dependent. See user manual for more information.
				"
			::= { spectrumAnalyserEntry 7 }

		
		-- 1.3.6.1.4.1.3715.100.2.10.1.8
		spectrumAnalyserValueTable OBJECT-TYPE
			SYNTAX OCTET STRING (SIZE (0..400))
			ACCESS read-only
			STATUS mandatory
			DESCRIPTION
				"A string of spectrum analyser level measurement values.
				Each octet in the string represents the level of the
				corresponding frequency in spectrumAnalyserChannelTable.
				
				Value scaling depends on the analyser type. With ACx and HDO
				analysers the unit is 0.5 dB."
			::= { spectrumAnalyserEntry 8 }

		
		-- 1.3.6.1.4.1.3715.100.2.10.1.9
		spectrumAnalyserHIHILimitTable OBJECT-TYPE
			SYNTAX OCTET STRING (SIZE (0..200))
			ACCESS read-write
			STATUS mandatory
			DESCRIPTION
				"A string of spectrum analyser level HIHI limit values.
				Each octet in the string represents the HIHI limit value 
				of the corresponding frequency in spectrumAnalyserChannelTable.
				
				Value scaling depends on the analyser type. With ACx and HDO
				analysers the unit is 0.5 dBuV.
				
				Value 0xFF indicates a non-used limit value."
			::= { spectrumAnalyserEntry 9 }

		
		-- 1.3.6.1.4.1.3715.100.2.10.1.10
		spectrumAnalyserHiLimitTable OBJECT-TYPE
			SYNTAX OCTET STRING (SIZE (0..200))
			ACCESS read-write
			STATUS mandatory
			DESCRIPTION
				"A string of spectrum analyser level Hi limit values.
				Each octet in the string represents the Hi limit value 
				of the corresponding frequency in spectrumAnalyserChannelTable.
				
				Value scaling depends on the analyser type. With ACx and HDO
				analysers the unit is 0.5 dBuV.
				
				Value 0xFF indicates a non-used limit value."
			::= { spectrumAnalyserEntry 10 }

		
		-- 1.3.6.1.4.1.3715.100.2.10.1.11
		spectrumAnalyserLoLimitTable OBJECT-TYPE
			SYNTAX OCTET STRING (SIZE (0..200))
			ACCESS read-write
			STATUS mandatory
			DESCRIPTION
				"A string of spectrum analyser level Lo limit values.
				Each octet in the string represents the Lo limit value 
				of the corresponding frequency in spectrumAnalyserChannelTable.
				
				Value scaling depends on the analyser type. With ACx and HDO
				analysers the unit is 0.5 dBuV.
				
				Value 0xFF indicates a non-used limit value."
			::= { spectrumAnalyserEntry 11 }

		
		-- 1.3.6.1.4.1.3715.100.2.10.1.12
		spectrumAnalyserLOLOLimitTable OBJECT-TYPE
			SYNTAX OCTET STRING (SIZE (0..200))
			ACCESS read-write
			STATUS mandatory
			DESCRIPTION
				"A string of spectrum analyser level LOLO limit values.
				Each octet in the string represents the LOLO limit value 
				of the corresponding frequency in spectrumAnalyserChannelTable.
				
				Value scaling depends on the analyser type. With ACx and HDO
				analysers the unit is 0.5 dBuV.
				
				Value 0xFF indicates a non-used limit value."
			::= { spectrumAnalyserEntry 12 }

		
		-- 1.3.6.1.4.1.3715.100.2.10.1.13
		spectrumAnalyserAlarmTolerance OBJECT-TYPE
			SYNTAX INTEGER (0..200)
			ACCESS read-write
			STATUS mandatory
			DESCRIPTION
				"Number of limits exceeded before a spectrum alarm or warning
				is activated. Common to all limit values.
				
				If limits are monitored separately and both are exceeding the
				tolerance, the higher severity alarm is raised."
			::= { spectrumAnalyserEntry 13 }

		
		-- 1.3.6.1.4.1.3715.100.2.10.1.14
		spectrumAnalyserSweepTime OBJECT-TYPE
			SYNTAX INTEGER
			ACCESS read-only
			STATUS mandatory
			DESCRIPTION
				"Spectrum analyser sweep time. Unit seconds."
			::= { spectrumAnalyserEntry 14 }

		
		-- 1.3.6.1.4.1.3715.100.2.10.1.15
		spectrumAnalyserStatus OBJECT-TYPE
			SYNTAX INTEGER
				{
				statusNormal(1),
				statusAlarm(2),
				statusWarning(3),
				statusWarningHi(4),
				statusAlarmHi(5),
				statusHwError(6)
				}
			ACCESS read-only
			STATUS mandatory
			DESCRIPTION
				"Analyser status:
				
				statusNormal(1) = the number of spectrum entries exceeding the limit values
				                  is lower than or equal to spectrumAnalyserAlarmTolerance value
				statusAlarm(2) = the number of spectrum entries exceeding the LOLO or HIHI limit values
				                   is higher than spectrumAnalyserAlarmTolerance value
				statusWarning(3) = the number of spectrum entries exceeding the Lo or Hi limit values
				                     is higher than spectrumAnalyserAlarmTolerance value
				statusWarningHi(4) = number of spectrum entries exceeding the Hi limit values
				                     is higher than spectrumAnalyserAlarmTolerance value
				statusAlarmHi(5) = number of spectrum entries exceeding the HIHI limit values
				                   is higher than spectrumAnalyserAlarmTolerance value
				statusHwError(6) = The analyser hardware has a fault
				
				This object has an entry in the discretePropertyTable."
			::= { spectrumAnalyserEntry 15 }

		
		-- 1.3.6.1.4.1.3715.100.2.10.1.16
		spectrumAnalyserChannelTypeByteTable OBJECT-TYPE
			SYNTAX OCTET STRING
			ACCESS read-write
			STATUS mandatory
			DESCRIPTION
				"A string of spectrum analyser level detector modes. Bytewise encoding, 
				each byte defines the detector mode for the corresponding
				frequency in spectrumAnalyserChannelTable.
				
				Currently defined values are:
				0 = Analog/PAL signal or unmodulated carrier
				1 = Digital/QAM (EU)/AnnexA (6.875 MHz) signal
				2 = WideBand (not supported; just reserved enumeration)
				3 = QAM (US)/AnnexB (5.4 MHz) signal
				4 = OFDM (6.0 MHz) signal
				5 = MinHold
				6 = MaxHold
				15 = Mode unset or unknown
				
				For legacy types Digital/QAM (EU)/AnnexA (1) (6.875 MHz) and analog/PAL (0) old spectrumAnalyserChannelTypeTable(7) can be used.
				Note that when using spectrumAnalyserChannelTypeTable(7) AnnexB and OFDM information is lost for all frequencies!
				 
				Maximum number of supported frequencies is device dependent. See user manual for more information.
				"
			::= { spectrumAnalyserEntry 16 }

		
	
	END

--
-- TELESTE-ANALYSER-MIB.mib
--
