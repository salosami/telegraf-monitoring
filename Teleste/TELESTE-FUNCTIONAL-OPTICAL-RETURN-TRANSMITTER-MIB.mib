--
-- TELESTE-FUNCTIONAL-OPTICAL-RETURN-TRANSMITTER-MIB.mib
-- MIB generated by MG-SOFT Visual MIB Builder 2013 (64-bit) Version 9.0  Build 760
-- Friday, March 14, 2014 at 08:39:53
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-OPTICAL-RETURN-TRANSMITTER-MIB
-- 
-- Description:   MIB module describing Teleste functional optical return transmitter interface specific objects
-- 
-- Revision history:
-- -----------------
-- 2, 14.3.2014, Sami Kuusisto
-- - Removed opticalReturnTransmitterBand because it is available at bandwidthValue.
-- 
-- 1, 12.3.2014, Sami Kuusisto
-- - Initial version.
-- 
-- ****************************************************************************
-- 

	TELESTE-FUNCTIONAL-OPTICAL-RETURN-TRANSMITTER-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.55
		opticalReturnTransmitter OBJECT IDENTIFIER ::= { functional 55 }

		
		-- 1.3.6.1.4.1.3715.100.55.1
		opticalReturnTransmitterTable OBJECT-TYPE
			SYNTAX SEQUENCE OF OpticalReturnTransmitterEntry
			ACCESS not-accessible
			STATUS mandatory
			DESCRIPTION
				"A table of return transmitter control entries."
			::= { opticalReturnTransmitter 1 }

		
		-- 1.3.6.1.4.1.3715.100.55.1.1
		opticalReturnTransmitterEntry OBJECT-TYPE
			SYNTAX OpticalReturnTransmitterEntry
			ACCESS not-accessible
			STATUS mandatory
			INDEX { functionalModuleId }
			::= { opticalReturnTransmitterTable 1 }

		
		OpticalReturnTransmitterEntry ::=
			SEQUENCE { 
				opticalReturnTransmitterLaserBias
					INTEGER,
				opticalReturnTransmitterPilotMode
					INTEGER,
				opticalReturnTransmitterPilotFrequency
					INTEGER
			 }

		-- 1.3.6.1.4.1.3715.100.55.1.1.1
		opticalReturnTransmitterLaserBias OBJECT-TYPE
			SYNTAX INTEGER
			ACCESS read-only
			STATUS mandatory
			DESCRIPTION
				"Return transmitter laser bias current. Unit 0.01 mA.
				This object has an entry in the propertyTable."
			::= { opticalReturnTransmitterEntry 1 }

		
		-- 1.3.6.1.4.1.3715.100.55.1.1.2
		opticalReturnTransmitterPilotMode OBJECT-TYPE
			SYNTAX INTEGER
				{
				on(1),
				off(2)
				}
			ACCESS read-write
			STATUS mandatory
			DESCRIPTION
				"Return transmitter pilot mode:
				1 = ON
				2 = OFF"
			::= { opticalReturnTransmitterEntry 2 }

		
		-- 1.3.6.1.4.1.3715.100.55.1.1.3
		opticalReturnTransmitterPilotFrequency OBJECT-TYPE
			SYNTAX INTEGER
				{
				freqUnknown(1),
				freqOther(2),
				freqLower(3),
				freqUpper(4)
				}
			ACCESS read-write
			STATUS mandatory
			DESCRIPTION
				"Return pilot frequency:
				1 = unknown pilot frequency
				2 = other pilot frequency
				3 = lower (4.5 / 5.5 MHz) pilot frequency
				4 = upper (6.5 MHz) pilot frequency"
			::= { opticalReturnTransmitterEntry 3 }

		
	
	END

--
-- TELESTE-FUNCTIONAL-OPTICAL-RETURN-TRANSMITTER-MIB.mib
--
