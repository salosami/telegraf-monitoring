--
-- TELESTE-FUNCTIONAL-PERFORMANCE-MIB.mib
-- MIB generated by MG-SOFT Visual MIB Builder 2021 (64-bit) Version 15.00  Build 1510
-- Friday, December 17, 2021 at 11:17:00
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-PERFORMANCE-MIB
-- 
-- Description:   MIB module describing Teleste functional performance interface specific objects
-- 
-- Revision history:
-- -----------------
-- 6, 17.12.2021, Sami Kuusisto
-- - Added 0 MHz enum to bandwidthValue.
-- 
-- 5, 9.9.2020, Sami Kuusisto
-- - Added new 1.8 GHz related enums to bandwidthValue.
-- 
-- 4, 20.12.2018, Sami Kuusisto
-- - Added new enums bandwidth42-53MHz, bandwidth117-147MHz and bandwidthFdx to bandwidthValue.
-- 
-- 3, 17.5.2017
-- - Fixed bandwidth descriptions.
-- 
-- 2, 13.3.2014, Sami Kuusisto
-- - added return path/diplexer options to bandwidthValue.
-- 
-- 1, 13.3.2014, Sami Kuusisto
-- - Initial version.
-- 
-- ****************************************************************************
-- 

	TELESTE-FUNCTIONAL-PERFORMANCE-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.92
		performance OBJECT IDENTIFIER ::= { functional 92 }

		
		-- 1.3.6.1.4.1.3715.100.92.1
		bandwidthTable OBJECT-TYPE
			SYNTAX SEQUENCE OF BandwidthEntry
			ACCESS not-accessible
			STATUS mandatory
			::= { performance 1 }

		
		-- 1.3.6.1.4.1.3715.100.92.1.1
		bandwidthEntry OBJECT-TYPE
			SYNTAX BandwidthEntry
			ACCESS not-accessible
			STATUS mandatory
			DESCRIPTION
				"A table for bandwidth options."
			INDEX { functionalModuleId }
			::= { bandwidthTable 1 }

		
		BandwidthEntry ::=
			SEQUENCE { 
				bandwidthValue
					INTEGER
			 }

		-- 1.3.6.1.4.1.3715.100.92.1.1.1
		bandwidthValue OBJECT-TYPE
			SYNTAX INTEGER
				{
				bandwidth862MHz(1),
				bandwidth1GHz(2),
				bandwidthNA(3),
				bandwidth606MHz(4),
				bandwidth1218MHz(5),
				bandwidthOther(6),
				bandwidthReserved7(7),
				bandwidthReserved8(8),
				bandwidth1794MHz(9),
				bandwidth30-47MHz(21),
				bandwidth65-85MHz(22),
				bandwidth85-108MHz(23),
				bandwidth204-258MHz(24),
				bandwidth42-53MHz(25),
				bandwidth117-147MHz(26),
				bandwidthFdx(27),
				bandwidth42-54MHz(31),
				bandwidth85-102MHz(32),
				bandwidth300-372MHz(33),
				bandwidth396-492MHz(34),
				bandwidth492-606MHz(35),
				bandwidth684-824MHz(36),
				bandwidth0MHz(37)
				}
			ACCESS read-write
			STATUS mandatory
			DESCRIPTION
				"Frequency range:
				1 = bandwidth862MHz - 862 MHz forward path
				2 = bandwidth1GHz - 1 GHz forward path
				3 = bandwidthNotAvailable - adjustable forward path band not supported
				4 = bandwidth606MHz - 606 MHz forward path
				5 = bandwidth1218MHz - 1.2 GHz forward path
				6 = bandwidthOther - other forward path band
				7 = bandwidthReserved
				8 = bandwidthReserved8
				9 = bandwidth1794MHz - 1.8 GHz forward path
				
				21 = bandwidth30-47MHz - 30/47 MHz
				22 = bandwidth65-85MHz - 65/85 MHz
				23 = bandwidth85-108MHz - 85/108 MHz
				24 = bandwidth204-258MHz - 204/258 MHz
				25 = bandwidth42-53MHz - 42/53 MHz
				26 = bandwidth117-147MHz - 117/147 MHz
				27 = bandwidthFdx - Full Duplex
				
				31 = bandwidth42-54MHz -  42/54 MHz
				32 = bandwidth85-102MHz - 85/102 MHz
				33 = bandwidth300-372MHz - 300/372 MHz
				34 = bandwidth396-492MHz - 396/492 MHz
				35 = bandwidth492-606MHz - 492/606 MHz
				36 = bandwidth684-824MHz - 684/834 MHz
				
				37 = bandwidth0MHz - 0 MHz
				"
			::= { bandwidthEntry 1 }

		
		-- 1.3.6.1.4.1.3715.100.92.2
		powersaveTable OBJECT-TYPE
			SYNTAX SEQUENCE OF PowersaveEntry
			ACCESS not-accessible
			STATUS mandatory
			::= { performance 2 }

		
		-- 1.3.6.1.4.1.3715.100.92.2.1
		powersaveEntry OBJECT-TYPE
			SYNTAX PowersaveEntry
			ACCESS not-accessible
			STATUS mandatory
			DESCRIPTION
				"A table for powersave options."
			INDEX { functionalModuleId }
			::= { powersaveTable 1 }

		
		PowersaveEntry ::=
			SEQUENCE { 
				powerSaveControl
					INTEGER,
				powerSaveStatus
					INTEGER
			 }

		-- 1.3.6.1.4.1.3715.100.92.2.1.1
		powerSaveControl OBJECT-TYPE
			SYNTAX INTEGER
				{
				powerSaveDisabled(1),
				powerSaveRF(2),
				powerSaveFull(3),
				powerSaveLaser(4),
				powerSaveAutomatic(5),
				powerSaveUnknown(6),
				powerSaveNA(7),
				powerSaveOther(8)
				}
			ACCESS read-write
			STATUS mandatory
			DESCRIPTION
				"Powersave mode adjustment (RF and/or laser when applicable)
				1: Normal powering/no powersave/powersave disabled (RF on, laser on)
				2: RF powersave (RF off, laser on). This is used, if only RF stages and no laser.
				3: Full powersave (RF off, laser off)
				4: Laser powersave (RF on, laser off). This is used, if only lasers and no RF stages.
				5: Automatic powersave
				6: Powersave state unknown
				7: Powersave not available
				8: Powersave state other
				"
			::= { powersaveEntry 1 }

		
		-- 1.3.6.1.4.1.3715.100.92.2.1.2
		powerSaveStatus OBJECT-TYPE
			SYNTAX INTEGER
				{
				powerSaveDisabled(1),
				powerSaveRF(2),
				powerSaveFull(3),
				powerSaveLaser(4),
				powerSaveAutomatic(5),
				powerSaveUnknown(6),
				powerSaveNA(7),
				powerSaveOther(8)
				}
			ACCESS read-write
			STATUS mandatory
			DESCRIPTION
				"Powersave status (RF and/or laser when applicable)
				1: Normal powering/no powersave/powersave disabled (RF on, laser on)
				2: RF powersave (RF off, laser on). This is used, if only RF stages and no laser.
				3: Full powersave (RF off, laser off)
				4: Laser powersave (RF on, laser off). This is used, if only lasers and no RF stagas.
				5: Automatic powersave
				6: Powersave state unknown
				7: Powersave not available
				8: Powersave state other
				"
			::= { powersaveEntry 2 }

		
		-- 1.3.6.1.4.1.3715.100.92.3
		rfPerformanceTable OBJECT-TYPE
			SYNTAX SEQUENCE OF RfPerformanceEntry
			ACCESS not-accessible
			STATUS mandatory
			::= { performance 3 }

		
		-- 1.3.6.1.4.1.3715.100.92.3.1
		rfPerformanceEntry OBJECT-TYPE
			SYNTAX RfPerformanceEntry
			ACCESS not-accessible
			STATUS mandatory
			DESCRIPTION
				"A table for performance options."
			INDEX { functionalModuleId }
			::= { rfPerformanceTable 1 }

		
		RfPerformanceEntry ::=
			SEQUENCE { 
				rfPerformanceControl
					INTEGER,
				rfPerformanceStatus
					INTEGER
			 }

		-- 1.3.6.1.4.1.3715.100.92.3.1.1
		rfPerformanceControl OBJECT-TYPE
			SYNTAX INTEGER
				{
				performanceAutomatic(1),
				performanceHigh(2),
				performanceStandard(3),
				performancePowerSave(4),
				performanceUnknown(6),
				performanceNA(7),
				performanceOther(8)
				}
			ACCESS read-write
			STATUS mandatory
			DESCRIPTION
				"RF performance adjustment:
				1 = automatic
				2 = high
				3 = standard
				4 = powersave
				
				6 = unknown
				7 = not available
				8 = other"
			::= { rfPerformanceEntry 1 }

		
		-- 1.3.6.1.4.1.3715.100.92.3.1.2
		rfPerformanceStatus OBJECT-TYPE
			SYNTAX INTEGER
				{
				performanceAutomatic(1),
				performanceHigh(2),
				performanceStandard(3),
				performancePowerSave(4),
				performanceUnknown(6),
				performanceNA(7),
				performanceOther(8)
				}
			ACCESS read-write
			STATUS mandatory
			DESCRIPTION
				"RF performance status:
				1 = automatic
				2 = high
				3 = standard
				4 = powersave
				
				6 = unknown
				7 = not available
				8 = other"
			::= { rfPerformanceEntry 2 }

		
	
	END

--
-- TELESTE-FUNCTIONAL-PERFORMANCE-MIB.mib
--
