--
-- TELESTE-FUNCTIONAL-PILOT-BASED-ALIGNMENT-MIB.mib
-- MIB generated by MG-SOFT Visual MIB Builder 2013 (64-bit) Version 9.0  Build 760
-- Wednesday, March 12, 2014 at 13:59:15
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-PILOT-BASED-ALIGNMENT-MIB
-- 
-- Description:   MIB module describing Teleste functional pilot based alignment interface specific objects
-- 
-- Revision history:
-- -----------------
-- 1, 10.3.2014, Sami Kuusisto
-- - Initial version.
-- 
-- ****************************************************************************
-- 

	TELESTE-FUNCTIONAL-PILOT-BASED-ALIGNMENT-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.84
		pilotBasedAlignment OBJECT IDENTIFIER ::= { functional 84 }

		
		-- 1.3.6.1.4.1.3715.100.84.1
		pilotBasedAlignmentTable OBJECT-TYPE
			SYNTAX SEQUENCE OF PilotBasedAlignmentEntry
			ACCESS not-accessible
			STATUS mandatory
			DESCRIPTION
				"A table of pilot based alignment settings."
			::= { pilotBasedAlignment 1 }

		
		-- 1.3.6.1.4.1.3715.100.84.1.1
		pilotBasedAlignmentEntry OBJECT-TYPE
			SYNTAX PilotBasedAlignmentEntry
			ACCESS not-accessible
			STATUS mandatory
			INDEX { functionalModuleId }
			::= { pilotBasedAlignmentTable 1 }

		
		PilotBasedAlignmentEntry ::=
			SEQUENCE { 
				pilotBasedAlignmentStart
					INTEGER,
				pilotBasedAlignmentStatus
					INTEGER
			 }

		-- 1.3.6.1.4.1.3715.100.84.1.1.1
		pilotBasedAlignmentStart OBJECT-TYPE
			SYNTAX INTEGER
				{
				pilotBasedAlignmentStart(1),
				pilotBasedAlignmentStartWriteOnly(2)
				}
			ACCESS read-write
			STATUS mandatory
			DESCRIPTION
				"Start pilot based alignment procedure.
				1: start alignment.
				2: reply when reading this object."
			::= { pilotBasedAlignmentEntry 1 }

		
		-- 1.3.6.1.4.1.3715.100.84.1.1.2
		pilotBasedAlignmentStatus OBJECT-TYPE
			SYNTAX INTEGER
				{
				pilotBasedAlignmentStatusNeverRun(1),
				pilotBasedAlignmentStatusRunning(2),
				pilotBasedAlignmentStatusSuccess(3),
				pilotBasedAlignmentStatusNoTunerModule(4),
				pilotBasedAlignmentStatusTargetsOutOfRange(5),
				pilotBasedAlignmentStatusInterStageSlopeOufOfRange(6),
				pilotBasedAlignmentStatusPilotsNotFound(7),
				pilotBasedAlignmentStatusInputSlopeOutOfRange(8),
				pilotBasedAlignmentStatusGainTargetOutOfRange(9),
				pilotBasedAlignmentStatusCableSimulatorNeeded(10),
				pilotBasedAlignmentStatusGainOrSlopeSaturated(11),
				pilotBasedAlignmentStatusUnknownForwardPathPlug(12),
				pilotBasedAlignmentStatusGain2TargetOutOfRange(13),
				pilotBasedAlignmentStatusInterStage2SlopeOutOfRange(14),
				pilotBasedAlignmentStatusOpticalInputPowerOutOfRange(15),
				pilotBasedAlignmentStatusWaitingForRun(16),
				pilotBasedAlignmentStatusCanceled(17)
				}
			ACCESS read-only
			STATUS mandatory
			DESCRIPTION
				"Status of last pilot based automatic aligment:
				 	1 = never run
				 	2 = running
				 	3 = success
				 	4 = no tuner module
				 	5 = targets out of range
				 	6 = interstage slope target ouf of range
				 	7 = pilots not found
				 	8 = input slope out of range
				 	9 = gain target out of range
				 	10 = a cable simulator may be needed into the universal plug-in slot
				 	11 = gain or slope is saturated
				 	12 = unknown forward path plug-in module
				 	13 = alignGain2TargetOutOfRange
				 	14 = alignInterStage2SlopeOutOfRange
				 	15 = alignOpticalInputPowerOutOfRange
				 	16 = alignWaitingForRun
				 	17 = alignCanceled"
			::= { pilotBasedAlignmentEntry 2 }

		
	
	END

--
-- TELESTE-FUNCTIONAL-PILOT-BASED-ALIGNMENT-MIB.mib
--
