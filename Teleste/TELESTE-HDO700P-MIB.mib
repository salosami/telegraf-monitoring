--
-- TELESTE-HDO700P-MIB.mib
-- MIB generated by MG-SOFT Visual MIB Builder Version 4.0 Build 349
-- Friday, November 19, 2010 at 09:32:38
--

-- ****************************************************************************
-- Copyright (c) 2005-2008 by:
--  
-- Teleste Corporation
-- Seponkatu 1
-- FIN-20660 Littoinen, Finland
-- tel. +358 2 2605 611
-- url: http://www.teleste.com
-- 
-- Description: HDO700P specific objects
-- 
-- Revision History:
-- -----------------
-- 1.1, 19.11.2010 Matti Susi
-- - added object oTxRfLevelTune
-- 
-- 1.0, 6.6.2008 Matti Susi
-- - initial release
-- 
-- ****************************************************************************

	TELESTE-HDO700P-MIB DEFINITIONS ::= BEGIN
 
		IMPORTS
			OBJECT-TYPE			
				FROM RFC-1212			
			oemodules			
				FROM TELESTE-HDO-MIB;
	
	
--
-- Node definitions
--
	
		-- 1.3.6.1.4.1.3715.14.2.1
		hdo700p OBJECT IDENTIFIER ::= { oemodules 1 }

		
		-- 1.3.6.1.4.1.3715.14.2.1.1
		oTx OBJECT IDENTIFIER ::= { hdo700p 1 }

		
		-- 1.3.6.1.4.1.3715.14.2.1.1.2
		oTxLaserIM OBJECT-TYPE
			SYNTAX INTEGER
			ACCESS read-only
			STATUS mandatory
			DESCRIPTION
				"Laser intermodulation setting. Unit 0.1?"
			::= { oTx 2 }

		
		-- 1.3.6.1.4.1.3715.14.2.1.1.3
		oTxLaserTemp OBJECT-TYPE
			SYNTAX INTEGER
			ACCESS read-only
			STATUS mandatory
			DESCRIPTION
				"Laser temperature. Unit 0.1 degC."
			::= { oTx 3 }

		
		-- 1.3.6.1.4.1.3715.14.2.1.1.4
		oTxLaserBias OBJECT-TYPE
			SYNTAX INTEGER
			ACCESS read-only
			STATUS mandatory
			DESCRIPTION
				"Laser bias current, Unit 0.1 mA."
			::= { oTx 4 }

		
		-- 1.3.6.1.4.1.3715.14.2.1.1.5
		oTxRfLevel OBJECT-TYPE
			SYNTAX INTEGER
			ACCESS read-only
			STATUS mandatory
			DESCRIPTION
				"RF Modulation level. Unit 0.1 dB."
			::= { oTx 5 }

		
		-- 1.3.6.1.4.1.3715.14.2.1.1.6
		oTxDC24V OBJECT-TYPE
			SYNTAX INTEGER
			ACCESS read-only
			STATUS mandatory
			DESCRIPTION
				"DC24V Voltage. Unit 0.1 volt."
			::= { oTx 6 }

		
		-- 1.3.6.1.4.1.3715.14.2.1.1.7
		oTxDC12V OBJECT-TYPE
			SYNTAX INTEGER
			ACCESS read-only
			STATUS mandatory
			DESCRIPTION
				"DC12V Voltage. Unit 0.1 volt."
			::= { oTx 7 }

		
		-- 1.3.6.1.4.1.3715.14.2.1.1.8
		oTxDC5V OBJECT-TYPE
			SYNTAX INTEGER
			ACCESS read-only
			STATUS mandatory
			DESCRIPTION
				"DC5V Voltage. Unit 0.1 volt."
			::= { oTx 8 }

		
		-- 1.3.6.1.4.1.3715.14.2.1.1.9
		oTxDCM5V OBJECT-TYPE
			SYNTAX INTEGER
			ACCESS read-only
			STATUS mandatory
			DESCRIPTION
				"-5VDC Voltage. Unit 0.1 volt."
			::= { oTx 9 }

		
		-- 1.3.6.1.4.1.3715.14.2.1.1.10
		oTxOpticalPower OBJECT-TYPE
			SYNTAX INTEGER
			ACCESS read-only
			STATUS mandatory
			DESCRIPTION
				"Optical output power. Unit 0.1 dBm."
			::= { oTx 10 }

		
		-- 1.3.6.1.4.1.3715.14.2.1.1.11
		oTxGainControlMode OBJECT-TYPE
			SYNTAX INTEGER
				{
				modeAGC(1),
				modeMGC(2)
				}
			ACCESS read-write
			STATUS mandatory
			DESCRIPTION
				"Gain Control mode. Values:
				1 = modeAGC, automatic level control
				2 = modeMGC, manual level control
				"
			::= { oTx 11 }

		
		-- 1.3.6.1.4.1.3715.14.2.1.1.12
		oTxSbsControl OBJECT-TYPE
			SYNTAX INTEGER (13 | 16 | 18)
			ACCESS read-write
			STATUS mandatory
			DESCRIPTION
				"SBS CONTROL Setting. Values:
				13
				16
				18"
			::= { oTx 12 }

		
		-- 1.3.6.1.4.1.3715.14.2.1.1.13
		oTxCTBControl OBJECT-TYPE
			SYNTAX INTEGER
				{
				ctbVideo(1),
				ctbCw(2)
				}
			ACCESS read-write
			STATUS mandatory
			DESCRIPTION
				"CTB control mode. Values:
				1 = ctbVideo
				2 = ctbCw"
			::= { oTx 13 }

		
		-- 1.3.6.1.4.1.3715.14.2.1.1.14
		oTxRfAttenuator OBJECT-TYPE
			SYNTAX INTEGER
			ACCESS read-write
			STATUS mandatory
			DESCRIPTION
				"RF attenuator setting. Unit 0.1 dB."
			::= { oTx 14 }

		
		-- 1.3.6.1.4.1.3715.14.2.1.1.15
		oTxLaserTempStatus OBJECT-TYPE
			SYNTAX INTEGER
				{
				normal(1),
				tempLOLO(2),
				tempLo(3),
				tempHi(4),
				tempHIHI(5)
				}
			ACCESS read-only
			STATUS mandatory
			DESCRIPTION
				"Laser temperature status.
				Monitored parameter - discretePropertyTable entry required."
			::= { oTx 15 }

		
		-- 1.3.6.1.4.1.3715.14.2.1.1.16
		oTxLaserBiasStatus OBJECT-TYPE
			SYNTAX INTEGER
				{
				biasNormal(1),
				biasLOLO(2),
				biasLo(3),
				biasHi(4),
				biasHIHI(5)
				}
			ACCESS read-only
			STATUS mandatory
			DESCRIPTION
				"Laser bias current status.
				Monitored parameter - discretePropertyTable entry required."
			::= { oTx 16 }

		
		-- 1.3.6.1.4.1.3715.14.2.1.1.17
		oTxLaserRfLevelStatus OBJECT-TYPE
			SYNTAX INTEGER
				{
				levelNormal(1),
				levelLOLO(2),
				levelLo(3),
				levelHi(4),
				levelHIHI(5)
				}
			ACCESS read-only
			STATUS mandatory
			DESCRIPTION
				"RF Modulation level status.
				Monitored parameter - discretePropertyTable entry required."
			::= { oTx 17 }

		
		-- 1.3.6.1.4.1.3715.14.2.1.1.18
		oTxOpticalPowerStatus OBJECT-TYPE
			SYNTAX INTEGER
				{
				powerNormal(1),
				powerLOLO(2),
				powerLo(3),
				powerHi(4),
				powerHIHI(5)
				}
			ACCESS read-only
			STATUS mandatory
			DESCRIPTION
				"Optical output power status.
				Monitored parameter - discretePropertyTable entry required."
			::= { oTx 18 }

		
		-- 1.3.6.1.4.1.3715.14.2.1.1.19
		oTxRfLevelTune OBJECT-TYPE
			SYNTAX INTEGER
				{
				tuneRead(0),
				tuneUp(1),
				tuneDown(2)
				}
			ACCESS read-write
			STATUS mandatory
			DESCRIPTION
				"Object is used for RF level tuning. Values:
				tuneRead(0)= value only for reading. If written, 'Bad value' is returned.
				tuneUp(1) = adjust level by +0.1 dB (up)
				tuneDown(2) = adjust level by -0.1 dB (down)"
			::= { oTx 19 }

		
	
	END

--
-- TELESTE-HDO700P-MIB.mib
--
