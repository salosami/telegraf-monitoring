--
-- TELESTE-FUNCTIONAL-TRAP-RECEIVERS-MIB.mib
-- MIB generated by MG-SOFT Visual MIB Builder 2021 (64-bit) Version 15.00  Build 1510
-- Friday, May 21, 2021 at 16:15:44
--

-- Teleste functional trap receiver MIB.
-- 
-- Version history (latest change at the top)
-- 
-- 1, 21.5.2021, Sami Kuusisto
-- - Initial version.
-- 
-- 

	TELESTE-FUNCTIONAL-TRAP-RECEIVERS-MIB DEFINITIONS ::= BEGIN
 
		IMPORTS
			OBJECT-GROUP			
				FROM SNMPv2-CONF			
			Integer32, OBJECT-TYPE, MODULE-IDENTITY			
				FROM SNMPv2-SMI			
			functional			
				FROM TELESTE-ROOT-MIB;
	
	
		-- 1.3.6.1.4.1.3715.100.105
		trapReceivers MODULE-IDENTITY 
			LAST-UPDATED "202105211200Z"		-- May 21, 2021 at 12:00 GMT
			ORGANIZATION 
				"Teleste Oyj"
			CONTACT-INFO 
				"support@teleste.com"
			DESCRIPTION 
				"Teleste functional MIB for trap receiver settings."
			::= { functional 105 }

		
	
--
-- Type definitions
--
	
-- Trap receiver mode.
-- 0: Trap receiver entry is not used. It's disabled.
-- 4: Use trap receiver as IPv4 address and send as IPv4 packet.
-- 6: Use trap receiver as IPv6 address and send as IPv6 packet.
		TrapReceiverMode ::= INTEGER
			{
			trapReceiverModeDisabled(0),
			trapReceiverModeIPv4(4),
			trapReceiverModeIPv6(6)
			}

	
--
-- Node definitions
--
	
		-- 1.3.6.1.4.1.3715.100.105.1
		trapReceiversNumberOfTrapReceiverEntries OBJECT-TYPE
			SYNTAX Integer32
			MAX-ACCESS read-only
			STATUS current
			DESCRIPTION
				"Number of trap receiver entries in trapReceiverTable."
			::= { trapReceivers 1 }

		
		-- 1.3.6.1.4.1.3715.100.105.2
		trapReceiversMaximumCommunityStringLength OBJECT-TYPE
			SYNTAX Integer32
			MAX-ACCESS read-only
			STATUS current
			DESCRIPTION
				"Maximum community string length supported by this device.
				All community string shares common maximum length."
			::= { trapReceivers 2 }

		
		-- 1.3.6.1.4.1.3715.100.105.3
		trapReceiversTable OBJECT-TYPE
			SYNTAX SEQUENCE OF TrapReceiversEntry
			MAX-ACCESS not-accessible
			STATUS current
			DESCRIPTION
				"Trap receiver table."
			::= { trapReceivers 3 }

		
		-- 1.3.6.1.4.1.3715.100.105.3.1
		trapReceiversEntry OBJECT-TYPE
			SYNTAX TrapReceiversEntry
			MAX-ACCESS not-accessible
			STATUS current
			DESCRIPTION
				"Trap receiver table."
			INDEX { trapReceiversTableIndex }
			::= { trapReceiversTable 1 }

		
		TrapReceiversEntry ::=
			SEQUENCE { 
				trapReceiversTableIndex
					Integer32,
				trapReceiverMode
					TrapReceiverMode,
				trapReceiverIpAddress
					OCTET STRING,
				trapReceiverCommunityString
					OCTET STRING
			 }

		-- 1.3.6.1.4.1.3715.100.105.3.1.1
		trapReceiversTableIndex OBJECT-TYPE
			SYNTAX Integer32 (1..128)
			MAX-ACCESS read-only
			STATUS current
			DESCRIPTION
				"Index to trapReceiverTable."
			::= { trapReceiversEntry 1 }

		
		-- 1.3.6.1.4.1.3715.100.105.3.1.2
		trapReceiverMode OBJECT-TYPE
			SYNTAX TrapReceiverMode
			MAX-ACCESS read-write
			STATUS current
			DESCRIPTION
				"Trap receiver mode.
				
				0: Trap receiver entry is not used. It's disabled.
				4: Use trap receiver as IPv4 address and send as IPv4 packet.
				6: Use trap receiver as IPv6 address and send as IPv6 packet."
			::= { trapReceiversEntry 2 }

		
		-- 1.3.6.1.4.1.3715.100.105.3.1.3
		trapReceiverIpAddress OBJECT-TYPE
			SYNTAX OCTET STRING
			MAX-ACCESS read-write
			STATUS current
			DESCRIPTION
				"IP address of Trap Receiver in network byte order. 
				
				Destination port is hard-coded 162.
				
				IPv4 address (a.b.c.d) (in IPv6 format): 0:0:0:0:0:FFFF:AABB:CCDD, where AA/BB/CC/DD is a/b/c/d as hex.
				IPv6 address: uses all 16 bytes
				"
			::= { trapReceiversEntry 3 }

		
		-- 1.3.6.1.4.1.3715.100.105.3.1.4
		trapReceiverCommunityString OBJECT-TYPE
			SYNTAX OCTET STRING (SIZE (0..255))
			MAX-ACCESS read-write
			STATUS current
			DESCRIPTION
				"Trap community string used with this trap receiver.
				
				Unused bytes (at the end) are filled with 0x00.
				
				Maximum commnity string lenght: See trapReceiversMaximumCommunityStringLength.
				"
			::= { trapReceiversEntry 4 }

		
		-- 1.3.6.1.4.1.3715.100.105.99
		trapReceiversConformance OBJECT IDENTIFIER ::= { trapReceivers 99 }

		
		-- 1.3.6.1.4.1.3715.100.105.99.1
		trapReceiversGroups OBJECT IDENTIFIER ::= { trapReceiversConformance 1 }

		
		-- 1.3.6.1.4.1.3715.100.105.99.1.1
		trapReceiversObjectGroup OBJECT-GROUP
			OBJECTS { trapReceiversNumberOfTrapReceiverEntries, trapReceiversMaximumCommunityStringLength, trapReceiversTableIndex, trapReceiverMode, trapReceiverIpAddress, 
				trapReceiverCommunityString }
			STATUS current
			DESCRIPTION 
				"Description."
			::= { trapReceiversGroups 1 }

		
	
	END

--
-- TELESTE-FUNCTIONAL-TRAP-RECEIVERS-MIB.mib
--
