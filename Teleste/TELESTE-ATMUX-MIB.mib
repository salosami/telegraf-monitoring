--
-- TELESTE-ATMUX-MIB.mib
-- MIB generated by MG-SOFT Visual MIB Builder Version 4.0 Build 349
-- Thursday, December 21, 2006 at 14:41:22
--

-- *****************************************************************************
-- Copyright (c) 2000-2006 by:
-- 
-- Teleste Corporation
-- Seponkatu 1
-- FIN-20660 Littoinen, Finland
-- tel. +358 2 2605 611
-- url: http://www.teleste.com
-- 
-- Description: ATmux module specific objects
-- 
-- Revision History:
-- -----------------
-- 1.0 21.12.2006 Matti Susi
-- - first offcial release
-- 
-- ****************************************************************************

	TELESTE-ATMUX-MIB DEFINITIONS ::= BEGIN
 
		IMPORTS
			OBJECT-TYPE			
				FROM RFC-1212			
			atmux			
				FROM TELESTE-ROOT-MIB;
	
	
--
-- Node definitions
--
	
		-- 1.3.6.1.4.1.3715.8.2
		coda OBJECT IDENTIFIER ::= { atmux 2 }

		
		-- 1.3.6.1.4.1.3715.8.3
		divisi OBJECT IDENTIFIER ::= { atmux 3 }

		
		-- 1.3.6.1.4.1.3715.8.3.1
		switchStatus OBJECT-TYPE
			SYNTAX INTEGER
				{
				switchNormal(1),
				switchBackup(2)
				}
			ACCESS read-only
			STATUS mandatory
			::= { divisi 1 }

		
		-- 1.3.6.1.4.1.3715.8.4
		legato OBJECT IDENTIFIER ::= { atmux 4 }

		
		-- 1.3.6.1.4.1.3715.8.5
		staccato OBJECT IDENTIFIER ::= { atmux 5 }

		
		-- 1.3.6.1.4.1.3715.8.6
		vivace OBJECT IDENTIFIER ::= { atmux 6 }

		
	
	END

--
-- TELESTE-ATMUX-MIB.mib
--
