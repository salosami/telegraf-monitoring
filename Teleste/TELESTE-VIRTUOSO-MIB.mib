--
-- TELESTE-VIRTUOSO-MIB.mib
-- MIB generated by MG-SOFT Visual MIB Builder Version 4.0 Build 349
-- Thursday, February 23, 2006 at 14:22:48
--

-- ****************************************************************************
-- Copyright (c) 2003-2006 by:
--  
-- Teleste Crporation
-- Seponkatu 1
-- FIN-20660 Littoinen, Finland
-- tel. +358 2 2605 611
-- url: http://www.teleste.com
--  
-- Module Name:   TELESTE-VIRTUOSO-MIB
--  
-- Description:   MIB module describing VIRTUOSO objects
--  
-- Revision History:
-- -----------------
-- 1.0, 26.03.2003 Perttu Fagerlund
-- - initial release
-- 
-- ****************************************************************************

	TELESTE-VIRTUOSO-MIB DEFINITIONS ::= BEGIN
 
		IMPORTS
			OBJECT-TYPE			
				FROM RFC-1212			
			TRAP-TYPE			
				FROM RFC-1215			
			Counter			
				FROM RFC1155-SMI			
			ifIndex, ifDescr			
				FROM RFC1213-MIB			
			atmux			
				FROM TELESTE-ROOT-MIB;
	
	
	
--
-- Node definitions
--
	
		-- 1.3.6.1.4.1.3715.8.51
		virtuoso OBJECT IDENTIFIER ::= { atmux 51 }

		
		-- 1.3.6.1.4.1.3715.8.51.1
		statusGroup OBJECT IDENTIFIER ::= { virtuoso 1 }

		
		-- 1.3.6.1.4.1.3715.8.51.1.1
		statusTemp OBJECT-TYPE
			SYNTAX INTEGER
				{
				normal(1),
				tempWarning(2),
				tempAlarm(3)
				}
			ACCESS read-only
			STATUS mandatory
			DESCRIPTION
				"Unit temperature status."
			::= { statusGroup 1 }

		
		-- 1.3.6.1.4.1.3715.8.51.1.2
		statusFan OBJECT-TYPE
			SYNTAX INTEGER
				{
				normal(1),
				warning(2),
				hwFailure(3)
				}
			ACCESS read-only
			STATUS mandatory
			DESCRIPTION
				"Status is Warning if one or several of the fans are 
				so worn-out that they are not expected to last long.
				
				Status is hwFailure if one or several of the fans are broken.
				Immediate changing is needed.
				"
			::= { statusGroup 2 }

		
		-- 1.3.6.1.4.1.3715.8.51.1.3
		statusOutputTable OBJECT-TYPE
			SYNTAX SEQUENCE OF StatusOutputEntry
			ACCESS not-accessible
			STATUS mandatory
			DESCRIPTION
				"A table of all QAM outputs and their status
				information."
			::= { statusGroup 3 }

		
		-- 1.3.6.1.4.1.3715.8.51.1.3.1
		statusOutputEntry OBJECT-TYPE
			SYNTAX StatusOutputEntry
			ACCESS not-accessible
			STATUS mandatory
			INDEX { ifIndex }
			::= { statusOutputTable 1 }

		
		StatusOutputEntry ::=
			SEQUENCE { 
				statusQamDescr
					OCTET STRING,
				statusHw
					INTEGER,
				statusOverflow
					INTEGER
			 }

		-- 1.3.6.1.4.1.3715.8.51.1.3.1.1
		statusQamDescr OBJECT-TYPE
			SYNTAX OCTET STRING
			ACCESS read-only
			STATUS mandatory
			DESCRIPTION
				"Copy of mib-2.ifTable.ifDescr for this interface"
			::= { statusOutputEntry 1 }

		
		-- 1.3.6.1.4.1.3715.8.51.1.3.1.2
		statusHw OBJECT-TYPE
			SYNTAX INTEGER
				{
				normal(1),
				failure(2)
				}
			ACCESS read-only
			STATUS mandatory
			DESCRIPTION
				"If such a HW failure exists that the device cannot
				reliable send data to this output the HWFailure status
				is set."
			::= { statusOutputEntry 2 }

		
		-- 1.3.6.1.4.1.3715.8.51.1.3.1.3
		statusOverflow OBJECT-TYPE
			SYNTAX INTEGER
				{
				normal(1),
				bufferOverflow(2)
				}
			ACCESS read-only
			STATUS mandatory
			DESCRIPTION
				"If there is too much data going to this output the 
				BufferOverflow status is set"
			::= { statusOutputEntry 3 }

		
		-- 1.3.6.1.4.1.3715.8.51.2
		measGroup OBJECT IDENTIFIER ::= { virtuoso 2 }

		
		-- 1.3.6.1.4.1.3715.8.51.2.1
		syncErrorCounter OBJECT-TYPE
			SYNTAX Counter
			ACCESS read-only
			STATUS mandatory
			DESCRIPTION
				"Total number of MPEG2 sync byte errors found in configured
				input streams."
			::= { measGroup 1 }

		
		-- 1.3.6.1.4.1.3715.8.51.2.2
		continuityErrorCounter OBJECT-TYPE
			SYNTAX Counter
			ACCESS read-only
			STATUS mandatory
			DESCRIPTION
				"Total number of continuity counter errors found in
				configured PIDs (in GbE input)"
			::= { measGroup 2 }

		
		-- 1.3.6.1.4.1.3715.8.51.2.3
		measOutputTable OBJECT-TYPE
			SYNTAX SEQUENCE OF MeasOutputEntry
			ACCESS not-accessible
			STATUS mandatory
			DESCRIPTION
				"A table of all QAM outputs and their measured values"
			::= { measGroup 3 }

		
		-- 1.3.6.1.4.1.3715.8.51.2.3.1
		measOutputEntry OBJECT-TYPE
			SYNTAX MeasOutputEntry
			ACCESS not-accessible
			STATUS mandatory
			INDEX { ifIndex }
			::= { measOutputTable 1 }

		
		MeasOutputEntry ::=
			SEQUENCE { 
				measQamDescr
					OCTET STRING,
				numberOfTSPackets
					Counter,
				outputSpeed
					Counter
			 }

		-- 1.3.6.1.4.1.3715.8.51.2.3.1.1
		measQamDescr OBJECT-TYPE
			SYNTAX OCTET STRING
			ACCESS read-only
			STATUS mandatory
			DESCRIPTION
				"Copy of mib-2.ifTable.ifDescr for this interface"
			::= { measOutputEntry 1 }

		
		-- 1.3.6.1.4.1.3715.8.51.2.3.1.2
		numberOfTSPackets OBJECT-TYPE
			SYNTAX Counter
			ACCESS read-only
			STATUS mandatory
			DESCRIPTION
				"The number of MPEG2 packets (188bytes) passed through
				this output, excluding null packets."
			::= { measOutputEntry 2 }

		
		-- 1.3.6.1.4.1.3715.8.51.2.3.1.3
		outputSpeed OBJECT-TYPE
			SYNTAX Counter
			ACCESS read-only
			STATUS mandatory
			DESCRIPTION
				"The average speed of this output in kb/s excluding null packets 
				measured between two last polls."
			::= { measOutputEntry 3 }

		
		-- 1.3.6.1.4.1.3715.8.51.2.4
		measFilterTable OBJECT-TYPE
			SYNTAX SEQUENCE OF MeasFilterEntry
			ACCESS not-accessible
			STATUS mandatory
			DESCRIPTION
				"A table of all configured input services and their 
				status information."
			::= { measGroup 4 }

		
		-- 1.3.6.1.4.1.3715.8.51.2.4.1
		measFilterEntry OBJECT-TYPE
			SYNTAX MeasFilterEntry
			ACCESS not-accessible
			STATUS mandatory
			INDEX { inputFilterIndex }
			::= { measFilterTable 1 }

		
		MeasFilterEntry ::=
			SEQUENCE { 
				inputFilterIndex
					INTEGER,
				inputFilterName
					OCTET STRING,
				inputFilterTSPackets
					Counter,
				inputFilterSyncErr
					Counter,
				inputFilterIPAddr
					OCTET STRING,
				inputFilterUDPPort
					OCTET STRING
			 }

		-- 1.3.6.1.4.1.3715.8.51.2.4.1.1
		inputFilterIndex OBJECT-TYPE
			SYNTAX INTEGER (1..512)
			ACCESS read-only
			STATUS mandatory
			DESCRIPTION
				"Index of the input service."
			::= { measFilterEntry 1 }

		
		-- 1.3.6.1.4.1.3715.8.51.2.4.1.2
		inputFilterName OBJECT-TYPE
			SYNTAX OCTET STRING
			ACCESS read-only
			STATUS mandatory
			DESCRIPTION
				"User-specified name of the input service."
			::= { measFilterEntry 2 }

		
		-- 1.3.6.1.4.1.3715.8.51.2.4.1.3
		inputFilterTSPackets OBJECT-TYPE
			SYNTAX Counter
			ACCESS read-only
			STATUS mandatory
			DESCRIPTION
				"The number of MPEG2 TS packets (188 bytes) matching this
				input filter."
			::= { measFilterEntry 3 }

		
		-- 1.3.6.1.4.1.3715.8.51.2.4.1.4
		inputFilterSyncErr OBJECT-TYPE
			SYNTAX Counter
			ACCESS read-only
			STATUS mandatory
			DESCRIPTION
				"The number of MPEG2 TS packets matching this
				input filter and having sync byte error."
			::= { measFilterEntry 4 }

		
		-- 1.3.6.1.4.1.3715.8.51.2.4.1.5
		inputFilterIPAddr OBJECT-TYPE
			SYNTAX OCTET STRING
			ACCESS read-only
			STATUS mandatory
			DESCRIPTION
				"IP addr / mask of this input service"
			::= { measFilterEntry 5 }

		
		-- 1.3.6.1.4.1.3715.8.51.2.4.1.6
		inputFilterUDPPort OBJECT-TYPE
			SYNTAX OCTET STRING
			ACCESS read-only
			STATUS mandatory
			DESCRIPTION
				"UDP addr / mask of this input service"
			::= { measFilterEntry 6 }

		
		-- 1.3.6.1.4.1.3715.8.51.2.5
		measPIDTable OBJECT-TYPE
			SYNTAX SEQUENCE OF MeasPIDEntry
			ACCESS not-accessible
			STATUS mandatory
			DESCRIPTION
				"A table of incoming PIDs inside all configured input filters. 
				A PID is shown in the list if it is configured (routed to output).
				
				NOTE: Only 50 first PIDs for each filters are shown.
				"
			::= { measGroup 5 }

		
		-- 1.3.6.1.4.1.3715.8.51.2.5.1
		measPIDEntry OBJECT-TYPE
			SYNTAX MeasPIDEntry
			ACCESS not-accessible
			STATUS mandatory
			INDEX { inputFilterIndex, pidNumber }
			::= { measPIDTable 1 }

		
		MeasPIDEntry ::=
			SEQUENCE { 
				filterNameOfPID
					OCTET STRING,
				pidNumber
					INTEGER,
				pidTSPackets
					Counter,
				pidCCErrorCounter
					Counter
			 }

		-- 1.3.6.1.4.1.3715.8.51.2.5.1.1
		filterNameOfPID OBJECT-TYPE
			SYNTAX OCTET STRING
			ACCESS read-only
			STATUS mandatory
			DESCRIPTION
				"User-specified name of the input service."
			::= { measPIDEntry 1 }

		
		-- 1.3.6.1.4.1.3715.8.51.2.5.1.2
		pidNumber OBJECT-TYPE
			SYNTAX INTEGER (0..8191)
			ACCESS read-only
			STATUS mandatory
			DESCRIPTION
				"The input PID number."
			::= { measPIDEntry 2 }

		
		-- 1.3.6.1.4.1.3715.8.51.2.5.1.3
		pidTSPackets OBJECT-TYPE
			SYNTAX Counter
			ACCESS read-only
			STATUS mandatory
			DESCRIPTION
				"The number of MPEG2 TS packets (188 bytes) received
				with this PID"
			::= { measPIDEntry 3 }

		
		-- 1.3.6.1.4.1.3715.8.51.2.5.1.4
		pidCCErrorCounter OBJECT-TYPE
			SYNTAX Counter
			ACCESS read-only
			STATUS mandatory
			DESCRIPTION
				"The number of MPEG2 packets received with this PID
				that had continuity counter error"
			::= { measPIDEntry 4 }

		
		-- 1.3.6.1.4.1.3715.8.51.2.6
		pidMonitor OBJECT IDENTIFIER ::= { measGroup 6 }

		
		-- 1.3.6.1.4.1.3715.8.51.2.6.1
		inputServToMonitor OBJECT-TYPE
			SYNTAX OCTET STRING
			ACCESS read-write
			STATUS mandatory
			DESCRIPTION
				"Specify the inputFilterName (list found in measFilterTable)
				that you want to monitor."
			::= { pidMonitor 1 }

		
		-- 1.3.6.1.4.1.3715.8.51.2.6.2
		monitorPIDTable OBJECT-TYPE
			SYNTAX SEQUENCE OF MonitorPIDEntry
			ACCESS not-accessible
			STATUS mandatory
			DESCRIPTION
				"A table of incoming PIDs (TSPacket counter nonzero) 
				and configured PIDs
				inside current service (inputServToMonitor)."
			::= { pidMonitor 2 }

		
		-- 1.3.6.1.4.1.3715.8.51.2.6.2.1
		monitorPIDEntry OBJECT-TYPE
			SYNTAX MonitorPIDEntry
			ACCESS not-accessible
			STATUS mandatory
			INDEX { inputFilterIndex, pidNumber }
			::= { monitorPIDTable 1 }

		
		MonitorPIDEntry ::=
			SEQUENCE { 
				monitorPIDNumber
					INTEGER,
				monitorPIDTSPackets
					Counter,
				monitorPIDCCErrorCounter
					Counter,
				monitorPIDSpeed
					Counter
			 }

		-- 1.3.6.1.4.1.3715.8.51.2.6.2.1.1
		monitorPIDNumber OBJECT-TYPE
			SYNTAX INTEGER (0..8191)
			ACCESS read-only
			STATUS mandatory
			DESCRIPTION
				"The input PID number."
			::= { monitorPIDEntry 1 }

		
		-- 1.3.6.1.4.1.3715.8.51.2.6.2.1.2
		monitorPIDTSPackets OBJECT-TYPE
			SYNTAX Counter
			ACCESS read-only
			STATUS mandatory
			DESCRIPTION
				"The number of MPEG2 TS packets (188 bytes) received
				with this PID"
			::= { monitorPIDEntry 2 }

		
		-- 1.3.6.1.4.1.3715.8.51.2.6.2.1.3
		monitorPIDCCErrorCounter OBJECT-TYPE
			SYNTAX Counter
			ACCESS read-only
			STATUS mandatory
			DESCRIPTION
				"The number of MPEG2 packets received with this PID
				that had continuity counter error"
			::= { monitorPIDEntry 3 }

		
		-- 1.3.6.1.4.1.3715.8.51.2.6.2.1.4
		monitorPIDSpeed OBJECT-TYPE
			SYNTAX Counter
			ACCESS read-only
			STATUS mandatory
			DESCRIPTION
				"The average speed in kb/s of the pid measured between two last polls.
				Speed is shown only in 20 first PIDs found in an input stream."
			::= { monitorPIDEntry 4 }

		
		-- 1.3.6.1.4.1.3715.8.51.2.7
		measCntrRst OBJECT-TYPE
			SYNTAX INTEGER
			ACCESS read-write
			STATUS mandatory
			DESCRIPTION
				"Writing a nonzero value to measCntrRst reset all counters 
				in virtuoso.measGroup.
				Returns always '0' when read."
			::= { measGroup 7 }

		
	
--
-- Trap definitions
--
	
		temperatureChange TRAP-TYPE 
			ENTERPRISE virtuoso
			VARIABLES { statusTemp }
			DESCRIPTION 
				"statusTemp has changed"
			::=  1

		fanStatusChange TRAP-TYPE 
			ENTERPRISE virtuoso
			VARIABLES { statusFan }
			DESCRIPTION 
				"statusFan has changed"
			::=  2

		hwErrOutput TRAP-TYPE 
			ENTERPRISE virtuoso
			VARIABLES { ifIndex, ifDescr }
			DESCRIPTION 
				"a QAM output defined by ifIndex is malfunctional"
			::=  3

		outputOverflow TRAP-TYPE 
			ENTERPRISE virtuoso
			VARIABLES { ifIndex, ifDescr }
			DESCRIPTION 
				"a QAM output defined by ifIndex is experiencing overflow"
			::=  4

		outputOverflowCleared TRAP-TYPE 
			ENTERPRISE virtuoso
			VARIABLES { ifIndex, ifDescr }
			DESCRIPTION 
				"outputOverflow warning condition is cleared for output interface ifIndex"
			::=  5

		highCCErrorRate TRAP-TYPE 
			ENTERPRISE virtuoso
			DESCRIPTION 
				"High number of Continuity Counter errors detected in configured MPEG streams."
			::=  6

		highCCErrorRateCleared TRAP-TYPE 
			ENTERPRISE virtuoso
			DESCRIPTION 
				"Rate of Continuity Counter errors is back to normal"
			::=  7

		highSyncErrorRate TRAP-TYPE 
			ENTERPRISE virtuoso
			DESCRIPTION 
				"High number of Sync errors detected in GBE input for configured filters."
			::=  8

		highSyncErrorRateCleared TRAP-TYPE 
			ENTERPRISE virtuoso
			DESCRIPTION 
				"Rate of Sync errors is back to normal"
			::=  9

	
	END

--
-- TELESTE-VIRTUOSO-MIB.mib
--
