--
-- TELESTE-ALSC-MIB.mib
-- MIB generated by MG-SOFT Visual MIB Builder 2018 (64-bit) Version 12.0  Build 1200
-- Monday, August 20, 2018 at 15:51:27
--

-- ****************************************************************************
-- Copyright (c) 2010 by:
-- 
-- Teleste Corporation
-- Seponkatu 1
-- FIN-20660 Littoinen, Finland
-- tel. +358 2 2605 611
-- url: http://www.teleste.com
-- 
-- Module Name:   TELESTE-ALSC-MIB
-- 
-- Description:   MIB module describing level control and ALSC functions
-- 
-- Revision History:
-- -----------------
-- 4, 20.8.2018, Sami Kuusisto, Rainer Salminen
-- - Added statusAlarm and statusWarning to controllerStatus.
-- 
-- 3, 17.6.2016, Sami Kuusisto
-- - Added statusAlscControlSaturated and statusAlscControlNearLimit to controllerStatus.
-- 
-- 2, 11.6.2010, Matti Susi
-- - first draft
-- 
-- 1, 24.6.2010, Matti Susi
-- - revised entire structure to make it as general as possible
-- 
-- ****************************************************************************

	TELESTE-ALSC-MIB DEFINITIONS ::= BEGIN
 
		IMPORTS
			OBJECT-TYPE			
				FROM RFC-1212			
			moduleId			
				FROM TELESTE-COMMON-MIB			
			functional			
				FROM TELESTE-ROOT-MIB;
	
	
--
-- Node definitions
--
	
-- Objects for level menasurement, control and control automation
		-- 1.3.6.1.4.1.3715.100.6
		levelManagement OBJECT IDENTIFIER ::= { functional 6 }

		
-- Level measurement objects
		-- 1.3.6.1.4.1.3715.100.6.1
		levelMeasurement OBJECT IDENTIFIER ::= { levelManagement 1 }

		
		-- 1.3.6.1.4.1.3715.100.6.1.1
		numberOfLevelDetectors OBJECT-TYPE
			SYNTAX INTEGER (0..8)
			ACCESS read-only
			STATUS mandatory
			DESCRIPTION
				"Number of signal monitors in this device. Zero means 
				that no signal monitors are available."
			::= { levelMeasurement 1 }

		
		-- 1.3.6.1.4.1.3715.100.6.1.2
		levelDetectorTable OBJECT-TYPE
			SYNTAX SEQUENCE OF LevelDetectorEntry
			ACCESS not-accessible
			STATUS mandatory
			::= { levelMeasurement 2 }

		
		-- 1.3.6.1.4.1.3715.100.6.1.2.1
		levelDetectorEntry OBJECT-TYPE
			SYNTAX LevelDetectorEntry
			ACCESS not-accessible
			STATUS mandatory
			INDEX { levelDetectorIndex }
			::= { levelDetectorTable 1 }

		
		LevelDetectorEntry ::=
			SEQUENCE { 
				levelDetectorIndex
					INTEGER,
				levelDetectorFrequency
					INTEGER,
				levelDetectorMeasuredLevel
					INTEGER,
				levelDetectorLostLevel
					INTEGER,
				levelDetectorUsage
					INTEGER,
				levelDetectorMode
					INTEGER,
				levelDetectorStatus
					INTEGER,
				levelDetectorTargetLevel
					INTEGER,
				levelDetectorTargetLevelStatus
					INTEGER,
				levelDetectorTargetLevelBackoff
					INTEGER,
				levelDetectorTargetLevelPrevAmp
					INTEGER
			 }

		-- 1.3.6.1.4.1.3715.100.6.1.2.1.1
		levelDetectorIndex OBJECT-TYPE
			SYNTAX INTEGER (1..10)
			ACCESS read-only
			STATUS mandatory
			DESCRIPTION
				"Unique index of the level detector."
			::= { levelDetectorEntry 1 }

		
		-- 1.3.6.1.4.1.3715.100.6.1.2.1.2
		levelDetectorFrequency OBJECT-TYPE
			SYNTAX INTEGER
			ACCESS read-write
			STATUS mandatory
			DESCRIPTION
				"Level detector frequency. Unit kHz.
				For a wideband detector the value is zero (read-only)."
			::= { levelDetectorEntry 2 }

		
		-- 1.3.6.1.4.1.3715.100.6.1.2.1.3
		levelDetectorMeasuredLevel OBJECT-TYPE
			SYNTAX INTEGER
			ACCESS read-only
			STATUS mandatory
			DESCRIPTION
				"Measured signal level. Unit 0.01 dBuV (dB for wideband signal monitor).
				This object has an entry in the propertyTable."
			::= { levelDetectorEntry 3 }

		
		-- 1.3.6.1.4.1.3715.100.6.1.2.1.4
		levelDetectorLostLevel OBJECT-TYPE
			SYNTAX INTEGER
			ACCESS read-write
			STATUS mandatory
			DESCRIPTION
				"A level value below which the signal is declared as 'lost'.
				Unit 0.01 dBuV."
			::= { levelDetectorEntry 4 }

		
		-- 1.3.6.1.4.1.3715.100.6.1.2.1.5
		levelDetectorUsage OBJECT-TYPE
			SYNTAX INTEGER
				{
				other(1),
				pilotHighMain(2),
				pilotHighReserve(3),
				pilotLowMain(4),
				pilotLowReserve(5),
				monitorSignal(6),
				monitorWideband(7)
				}
			ACCESS read-only
			STATUS mandatory
			DESCRIPTION
				"Use of the level measurement:
				other(1) = Other
				pilotHighMain(2) = Main high pilot
				pilotHighReserve(3) = Reserve high pilot
				pilotLowMain(4) = Main low pilot
				pilotLowReserve(5) = Reserve low pilot
				monitorSignal(6) = Signal monitor
				monitorWideband(7) = Wideband signal monitor
				
				Target levels exist only for entry types 2...5."
			::= { levelDetectorEntry 5 }

		
		-- 1.3.6.1.4.1.3715.100.6.1.2.1.6
		levelDetectorMode OBJECT-TYPE
			SYNTAX INTEGER
				{
				modeAnalog(1),
				modeQam(2),
				modeWideband(3)
				}
			ACCESS read-write
			STATUS mandatory
			DESCRIPTION
				"Level detector operating mode:
				modeAnalog(1) = analog - analogue TV channel or carrier (pilot)
				modeQam(2) = QAM - QAM channel or noise
				modeWideband(3) = wideband signal power monitor (read only)"
			::= { levelDetectorEntry 6 }

		
		-- 1.3.6.1.4.1.3715.100.6.1.2.1.7
		levelDetectorStatus OBJECT-TYPE
			SYNTAX INTEGER
				{
				levelNormal(1),
				levelHIHI(2),
				levelHI(3),
				levelLO(4),
				levelLOLO(5)
				}
			ACCESS read-only
			STATUS mandatory
			DESCRIPTION
				"Level status:
				levelNormal(1) = normal
				levelHIHI(2)3 = hifg alarm
				levelHI(3) = high warning
				levelLO(4) = low warning
				levelLOLO(5) = low alarm
				This object has an entry in the discretePropertyTable (only instances
				with levelDetectorUsage values 2...5 (pilots))."
			::= { levelDetectorEntry 7 }

		
		-- 1.3.6.1.4.1.3715.100.6.1.2.1.8
		levelDetectorTargetLevel OBJECT-TYPE
			SYNTAX INTEGER
			ACCESS read-write
			STATUS mandatory
			DESCRIPTION
				"Target level value used for automatic level control. Unit 0.01 dBuV."
			::= { levelDetectorEntry 8 }

		
		-- 1.3.6.1.4.1.3715.100.6.1.2.1.9
		levelDetectorTargetLevelStatus OBJECT-TYPE
			SYNTAX INTEGER
				{
				useActive(1),
				useStandby(2),
				useDisabled(3)
				}
			ACCESS read-only
			STATUS mandatory
			DESCRIPTION
				"Level detector status for automatic control:
				1 = Active - the pilot is in use and controlling ALSC
				2 = Standby - the pilot is not in use (backup or missing)
				3 = Disabled - the pilot is not in use"
			::= { levelDetectorEntry 9 }

		
		-- 1.3.6.1.4.1.3715.100.6.1.2.1.10
		levelDetectorTargetLevelBackoff OBJECT-TYPE
			SYNTAX INTEGER (-1500..500)
			ACCESS read-write
			STATUS mandatory
			DESCRIPTION
				"Pilot target level backoff value. Unit 0.01 dB."
			::= { levelDetectorEntry 10 }

		
		-- 1.3.6.1.4.1.3715.100.6.1.2.1.11
		levelDetectorTargetLevelPrevAmp OBJECT-TYPE
			SYNTAX INTEGER
			ACCESS read-write
			STATUS mandatory
			DESCRIPTION
				"Pilot target level value of the previous amplifier in cascade.
				Unit 0.01 dBuV."
			::= { levelDetectorEntry 11 }

		
-- Level control (gain and slope) objects
		-- 1.3.6.1.4.1.3715.100.6.2
		levelControl OBJECT IDENTIFIER ::= { levelManagement 2 }

		
		-- 1.3.6.1.4.1.3715.100.6.2.1
		numberOfLevelControlElements OBJECT-TYPE
			SYNTAX INTEGER (0..8)
			ACCESS read-only
			STATUS mandatory
			DESCRIPTION
				"The number of level control modules available in this 
				device. Zero value means that no level control modules 
				are installed."
			::= { levelControl 1 }

		
		-- 1.3.6.1.4.1.3715.100.6.2.5
		levelControlElementTable OBJECT-TYPE
			SYNTAX SEQUENCE OF LevelControlElementEntry
			ACCESS not-accessible
			STATUS mandatory
			DESCRIPTION
				"A table of gain and slope control entries. Index = module table index.
				Integrated gain and slope controls are handled as modules, e.g. they
				must have module table entries."
			::= { levelControl 5 }

		
		-- 1.3.6.1.4.1.3715.100.6.2.5.1
		levelControlElementEntry OBJECT-TYPE
			SYNTAX LevelControlElementEntry
			ACCESS not-accessible
			STATUS mandatory
			DESCRIPTION
				"Uniques index of the level control element"
			INDEX { levelControlElementIndex }
			::= { levelControlElementTable 1 }

		
		LevelControlElementEntry ::=
			SEQUENCE { 
				levelControlElementIndex
					INTEGER,
				levelControlElementType
					INTEGER,
				levelControlElementRole
					INTEGER,
				levelControlElementValue
					INTEGER,
				levelControlElementPresetValue
					INTEGER,
				levelControlElementStatus
					INTEGER
			 }

		-- 1.3.6.1.4.1.3715.100.6.2.5.1.1
		levelControlElementIndex OBJECT-TYPE
			SYNTAX INTEGER (1..10)
			ACCESS read-only
			STATUS mandatory
			::= { levelControlElementEntry 1 }

		
		-- 1.3.6.1.4.1.3715.100.6.2.5.1.2
		levelControlElementType OBJECT-TYPE
			SYNTAX INTEGER
				{
				typeOther(1),
				typeGain(2),
				typeSlope(3)
				}
			ACCESS read-write
			STATUS mandatory
			DESCRIPTION
				"Type of level controller:
				typeOther(1) = other control element
				typeGain(2) = gain control element (attenuator)
				typeSlope(3) = slope control element (equaliser)"
			::= { levelControlElementEntry 2 }

		
		-- 1.3.6.1.4.1.3715.100.6.2.5.1.3
		levelControlElementRole OBJECT-TYPE
			SYNTAX INTEGER
				{
				controlInput(1),
				controlInterstage(2),
				controlTotal(3),
				controlReturnPath(4),
				controlOther(5)
				}
			ACCESS read-only
			STATUS mandatory
			DESCRIPTION
				"Level control element role:
				controlInput(1) = input
				controlInterstage(2) = interstage
				controlTotal(3) = total gain
				controlReturnPath(4) = return path
				controlOther(5) = other"
			::= { levelControlElementEntry 3 }

		
		-- 1.3.6.1.4.1.3715.100.6.2.5.1.4
		levelControlElementValue OBJECT-TYPE
			SYNTAX INTEGER
			ACCESS read-write
			STATUS mandatory
			DESCRIPTION
				"Control element value. Unit 0.01 dB."
			::= { levelControlElementEntry 4 }

		
		-- 1.3.6.1.4.1.3715.100.6.2.5.1.5
		levelControlElementPresetValue OBJECT-TYPE
			SYNTAX INTEGER
			ACCESS read-write
			STATUS mandatory
			DESCRIPTION
				"Default 'Go to' value used e.g. when all pilots are lost. Unit 0.01 dB."
			::= { levelControlElementEntry 5 }

		
		-- 1.3.6.1.4.1.3715.100.6.2.5.1.6
		levelControlElementStatus OBJECT-TYPE
			SYNTAX INTEGER
				{
				statusNormal(1),
				statusMinimum(2),
				statusMaximum(3),
				statusFrozen(4),
				statusDefault(5)
				}
			ACCESS read-only
			STATUS mandatory
			DESCRIPTION
				"Level control element status:
				statusNormal(1) = normal
				statusMinimum(2) = minimum
				statusMaximum(3) = maximum
				statusFrozen(4) = frozen (ALSC on but no pilots are detected)
				statusDefault(5) = default (ALSC on but no pilots are detected)
				
				This object has an entry in the discretePropertyTable.
				
				Returns value 'normal' when ALSC is not enabled."
			::= { levelControlElementEntry 6 }

		
-- Level control automation (ALSC) specific objects
		-- 1.3.6.1.4.1.3715.100.6.3
		levelControlAutomation OBJECT IDENTIFIER ::= { levelManagement 3 }

		
		-- 1.3.6.1.4.1.3715.100.6.3.1
		numberOfLevelControllers OBJECT-TYPE
			SYNTAX INTEGER (0..8)
			ACCESS read-only
			STATUS mandatory
			DESCRIPTION
				"Number of ALSC modules in this device. Zero means 
				that the ALSC function is not available.
				"
			::= { levelControlAutomation 1 }

		
		-- 1.3.6.1.4.1.3715.100.6.3.2
		levelControllerButtonMode OBJECT-TYPE
			SYNTAX INTEGER
				{
				buttonEnable(1),
				buttonDisable(2),
				buttonNotAvailable(3)
				}
			ACCESS read-write
			STATUS mandatory
			DESCRIPTION
				"Activation/deactivation of the local alignment button:
				1 = buttonEnable - pressing the local button start automatic forward path alignment
				2 = buttonDisable - pressing the local button has no effect
				3 = buttonNotAvailable - the platform has no alignment button"
			::= { levelControlAutomation 2 }

		
		-- 1.3.6.1.4.1.3715.100.6.3.3
		controllerTable OBJECT-TYPE
			SYNTAX SEQUENCE OF ControllerEntry
			ACCESS not-accessible
			STATUS mandatory
			::= { levelControlAutomation 3 }

		
		-- 1.3.6.1.4.1.3715.100.6.3.3.1
		controllerEntry OBJECT-TYPE
			SYNTAX ControllerEntry
			ACCESS not-accessible
			STATUS mandatory
			INDEX { controllerIndex }
			::= { controllerTable 1 }

		
		ControllerEntry ::=
			SEQUENCE { 
				controllerIndex
					INTEGER,
				controllerMode
					INTEGER,
				controllerStatus
					INTEGER,
				controllerPilotLostAction
					INTEGER,
				controllerStartAlignment
					INTEGER,
				controllerAlignmentStatus
					INTEGER
			 }

		-- 1.3.6.1.4.1.3715.100.6.3.3.1.1
		controllerIndex OBJECT-TYPE
			SYNTAX INTEGER (1..10)
			ACCESS read-write
			STATUS mandatory
			DESCRIPTION
				"Unique index of the automatic level controller."
			::= { controllerEntry 1 }

		
		-- 1.3.6.1.4.1.3715.100.6.3.3.1.2
		controllerMode OBJECT-TYPE
			SYNTAX INTEGER
				{
				modeManual(1),
				modeIntelligent(2),
				modeALSC(3),
				modeALC(4),
				modeOLC(5)
				}
			ACCESS read-write
			STATUS mandatory
			DESCRIPTION
				"Controller operating mode:
				modeManual(1) = all gain and slope controls must be manually adjusted
				modeIntelligent(2) = only total gain can be adjusted, individual gain control
				elements are adjusted based on total gain. Slope controls must be manually adjusted.
				modeALSC(3) = gain and slope are automatically adjusted based on pilot levels
				modeALC(4) = gain is automatically adjusted based on pilot levels
				modeOLC = gain is automatically adjusted based on optical input level"
			::= { controllerEntry 2 }

		
		-- 1.3.6.1.4.1.3715.100.6.3.3.1.3
		controllerStatus OBJECT-TYPE
			SYNTAX INTEGER
				{
				statusNormal(1),
				statusMainPilotsMissing(2),
				statusOnePilotOnly(3),
				statusAllPilotsMissing(4),
				statusTunerError(5),
				statusControlDisabled(6),
				statusAlscControlSaturated(7),
				statusAlscControlNearLimit(8),
				statusAlarm(9),
				statusWarning(10)
				}
			ACCESS read-write
			STATUS mandatory
			DESCRIPTION
				"Controller status:
				statusNormal(1) = ALSC is functioning normally
				statusMainPilotsMissing = ALSC is running on backup pilots
				statusOnePilotOnly(3 = ALSC is running on one pilot only and control
				accuracy might be worse than normal
				statusAllPilotsMissing(4) = all pilots are missing
				statusTunerError(5) = an error has been detected in the tuner, which may compromise level measurement accuracy
				statusControlDisabled(6) = ALSC is switched off
				statusAlscControlSaturated(7) = One or more ALSC controls (gain, slope) is saturated
				statusAlscControlNearLimit(8) = One or more ALSC controls (gain, slope) is near limit
				statusAlarm(9) = ALSC has an unspecified alarm condition
				statusWarning(10) = ALSC has an unspecified warning condition
				
				Only highest priority state is shown. Note that supported states are device dependent.
				
				Priority order (highest priority first)
				- statusControlDisabled
				- statusTunerError
				- statusAllPilotsMissing
				- statusOnePilotOnly
				- statusMainPilotsMissing
				- statusAlscControlSaturated
				- statusAlscControlNearLimit
				- statusAlarm
				- statusWarning
				- statusNormal
				
				
				"
			::= { controllerEntry 3 }

		
		-- 1.3.6.1.4.1.3715.100.6.3.3.1.4
		controllerPilotLostAction OBJECT-TYPE
			SYNTAX INTEGER
				{
				freeze(1),
				preset(2)
				}
			ACCESS read-write
			STATUS mandatory
			DESCRIPTION
				"Controller behaviour when all pilots are lost:
				freeze(1) = freeze gain and slope to current values
				preset(2) = set gain and slope to preset values (levelControlElementPresetValue)"
			::= { controllerEntry 4 }

		
		-- 1.3.6.1.4.1.3715.100.6.3.3.1.5
		controllerStartAlignment OBJECT-TYPE
			SYNTAX INTEGER
				{
				alignForward(1),
				alignReturn(2),
				alignBoth(3),
				alignNotAvailable(4),
				alignForwardOMIBased(5)
				}
			ACCESS read-write
			STATUS mandatory
			DESCRIPTION
				"This object is used to start the intelligent gain alignment prodecure:
				alignForward(1) = writing this value starts the forward path alignment procedure
				alignReturn(2) = writing this value starts the return path alignment procedure
				alignBoth(3) = writing this value starts the alignment procedure for both paths
				alignNotAvailable(4) = the device does not support intelligent alignment
				alignForwardOMIBased(5) = writing this value starts the forward path
				alignment procedure based on optical OMI
				When reading, this object always returns value 'alignNotAvailable'."
			::= { controllerEntry 5 }

		
		-- 1.3.6.1.4.1.3715.100.6.3.3.1.6
		controllerAlignmentStatus OBJECT-TYPE
			SYNTAX INTEGER
				{
				alignNeverRun(1),
				alignRunning(2),
				alignSuccess(3),
				alignNoTuner(4),
				alignTargetsOutOfRange(5),
				alignInterStageSlopeOutOfRange(6),
				alignPilotsNotFound(7),
				alignInputSlopeOutOfRange(8),
				alignGainTargetOutOfRange(9),
				alignCableSimulatorNeeded(10),
				alignGainOrSlopeSaturated(11),
				alignUnknownForwardPathPlug(12),
				alignGain2TargetOutOfRange(13),
				alignInterStage2SlopeOutOfRange(14),
				alignOpticalInputPowerOutOfRange(15)
				}
			ACCESS read-write
			STATUS mandatory
			DESCRIPTION
				"Status of last forward path automatic aligment:
				alignNeverRun(1) = never run
				alignRunning(2) = running
				alignSuccess(3) = success
				alignNoTuner(4) = no tuner module
				alignTargetsOutOfRange(5) = targets out of range
				alignInterStageSlopeOutOfRange(6) = interstage slope target ouf of range
				alignPilotsNotFound(7) = pilots not found
				alignInputSlopeOutOfRange(8) = input slope out of range
				alignGainTargetOutOfRange(9) = gain target out of range
				alignCableSimulatorNeeded(10) = a cable simulator may be needed into the universal plug-in slot
				alignGainOrSlopeSaturated(11) = gain or slope is saturated
				alignUnknownForwardPathPlug(12) = unknown forward path plug-in module
				alignGain2TargetOutOfRange(13) = alignGain2TargetOutOfRange
				alignInterStage2SlopeOutOfRange(14) = alignInterStage2SlopeOutOfRange
				alignOpticalInputPowerOutOfRange(15) = alignOpticalInputPowerOutOfRange
				When alscControlMode is set to 'manual' or 'ALSC' this object always returns
				value neverRun(1)."
			::= { controllerEntry 6 }

		
	
	END

--
-- TELESTE-ALSC-MIB.mib
--
