--
-- TELESTE-HMSMODEM-MIB.mib
-- MIB generated by MG-SOFT Visual MIB Builder Version 4.0 Build 349
-- Monday, March 19, 2012 at 14:07:31
--

-- ****************************************************************************
-- Copyright (c) 2003-2012 by:
-- 
-- Teleste Corporation
-- Seponkatu 1
-- FIN-20660 Littoinen, Finland
-- tel. +358 2 2605 611
-- url: http://www.teleste.com
-- 
-- Module Name: TELESTE-HMSMODEM-MIB
-- 
-- Description: MIB module describing common objects for a HMS
--              modem in any Teleste transponder
-- 
-- Revision History:
-- -----------------
-- 13, 16.3.2012, Sami Halen
-- - added modemProtocol
-- - updated modemStatusRxLevel to use ValueStatus from TELESTE-ROOT-MIB
-- 
-- 1.12, 6.2.2008, Matti Susi
-- - added object modemStatusRxLevel
-- 
-- 1.11, 13.4.2007, Matti Susi
-- - restored object numbering to version 1.0
-- 
-- 1.1,  21.9.2004, Matti Susi
-- - modemTxLevelMin renamed to modemTxLevel
-- - added object modemScanEnable
-- 
-- 1.0,  1.9.2004, Matti Susi
-- - First official release
-- 
-- ****************************************************************************

	TELESTE-HMSMODEM-MIB DEFINITIONS ::= BEGIN
 
		IMPORTS
			OBJECT-TYPE			
				FROM RFC-1212			
			functional, ValueStatus			
				FROM TELESTE-ROOT-MIB;
	
	
	
--
-- Node definitions
--
	
		-- 1.3.6.1.4.1.3715.100.1
		hmsModem OBJECT IDENTIFIER ::= { functional 1 }

		
-- Transponder RF modem specific objects
-- 
		-- 1.3.6.1.4.1.3715.100.1.1
		modemSettings OBJECT IDENTIFIER ::= { hmsModem 1 }

		
		-- 1.3.6.1.4.1.3715.100.1.1.1
		modemRxLevel OBJECT-TYPE
			SYNTAX INTEGER
			ACCESS read-only
			STATUS mandatory
			DESCRIPTION
				"Modem receive level. Unit 0.01 dBuV."
			::= { modemSettings 1 }

		
		-- 1.3.6.1.4.1.3715.100.1.1.2
		modemRxFrequency OBJECT-TYPE
			SYNTAX INTEGER
			ACCESS read-only
			STATUS mandatory
			DESCRIPTION
				"Modem receive frequency. Unit kHz."
			::= { modemSettings 2 }

		
		-- 1.3.6.1.4.1.3715.100.1.1.3
		modemRxScanMin OBJECT-TYPE
			SYNTAX INTEGER
			ACCESS read-write
			STATUS mandatory
			DESCRIPTION
				"Modem receive scanning minimum frequency. Unit kHz."
			::= { modemSettings 3 }

		
		-- 1.3.6.1.4.1.3715.100.1.1.4
		modemRxScanMax OBJECT-TYPE
			SYNTAX INTEGER
			ACCESS read-write
			STATUS mandatory
			DESCRIPTION
				"Modem receive scanning maximum frequency. Unit kHz."
			::= { modemSettings 4 }

		
		-- 1.3.6.1.4.1.3715.100.1.1.5
		modemTxFrequency OBJECT-TYPE
			SYNTAX INTEGER
			ACCESS read-only
			STATUS mandatory
			DESCRIPTION
				"Modem transmit frequency. Unit kHz."
			::= { modemSettings 5 }

		
		-- 1.3.6.1.4.1.3715.100.1.1.6
		modemTxLevel OBJECT-TYPE
			SYNTAX INTEGER
			ACCESS read-write
			STATUS mandatory
			DESCRIPTION
				"Current modem transmit level. Unit 0.01 dBµV.
				Value range:
				- maximum is limited by the current modemTxLevelMax
				- minimum value is limited by the modem hardware"
			::= { modemSettings 6 }

		
		-- 1.3.6.1.4.1.3715.100.1.1.7
		modemTxLevelMax OBJECT-TYPE
			SYNTAX INTEGER
			ACCESS read-write
			STATUS mandatory
			DESCRIPTION
				"Modem maximum transmit level. Unit 0.01 dBµV.
				Value range:
				- maximum is limited by the current hardware
				- minimum value is the current modemTxLevel value"
			::= { modemSettings 7 }

		
		-- 1.3.6.1.4.1.3715.100.1.1.8
		modemRegState OBJECT-TYPE
			SYNTAX INTEGER
				{
				regSettingRx(1),
				regNoCarrier(2),
				regWaitChannelInfo(3),
				regSettingTxFreq(4),
				regTxStabilisation(5),
				regSettingTxLevel(6),
				regPreparing(7),
				regStarting(8),
				regInProgress(9),
				regWaitConfirm(10),
				regComplete(11)
				}
			ACCESS read-only
			STATUS mandatory
			DESCRIPTION
				"Modem registration state:
				1 = setting RX frequency
				2 = no data carrier
				3 = waiting for channel infor (CHNLDESC)
				4 = setting TX frequency
				5 = waiting for TX stabilisation
				6 = setting TX level
				7 = preparing registration
				8 = registration started
				9 = registration in progress
				10 = waiting for confimation
				11 = registration complete"
			::= { modemSettings 8 }

		
		-- 1.3.6.1.4.1.3715.100.1.1.13
		modemChnlDescTimeout OBJECT-TYPE
			SYNTAX INTEGER
			ACCESS read-write
			STATUS mandatory
			DESCRIPTION
				"Timeout for CHNLDESC. Unit 1 second.
				
				This is the time the modem waits for a valid CHNLDESC message
				from the HMTS. If the timeout is exceeded, the modem starts
				scanning for another HMS data channel.
				
				Timeout value 0 means the modem will wait an infinite time
				if it has found a signal with sufficient level."
			::= { modemSettings 13 }

		
		-- 1.3.6.1.4.1.3715.100.1.1.14
		modemPollTimeout OBJECT-TYPE
			SYNTAX INTEGER
			ACCESS read-write
			STATUS mandatory
			DESCRIPTION
				"Timeout for unicast messages. Unit 1 second.
				
				This is the time the modem waits for any messages to its
				unicast MAC address. If the timeout is exceeded, the modem
				starts the registration process to inform the HMTS about
				it's presence.
				
				Value 0 will disable poll checking (contention mode operation)."
			::= { modemSettings 14 }

		
		-- 1.3.6.1.4.1.3715.100.1.1.15
		modemScanEnable OBJECT-TYPE
			SYNTAX INTEGER
				{
				scanEnabled(1),
				scanDisabled(2)
				}
			ACCESS read-write
			STATUS mandatory
			DESCRIPTION
				"Modem forward data channel scanning control:
				1 = scanning is enabled
				2 = scanning is disabled (fixed frequency operation)"
			::= { modemSettings 15 }

		
		-- 1.3.6.1.4.1.3715.100.1.1.16
		modemProtocol  OBJECT-TYPE
			SYNTAX INTEGER
				{
				catvisor(1),
				hms(2)
				}
			ACCESS read-write
			STATUS mandatory
			DESCRIPTION
				"Modem protocol in use.
				Writing this object resets the unit and changes the protocol
				and may thus cause loss of remote connection.
				All communication settings should be reviewed carefully
				before writing this object.
				1 = CATVisor (Teleste proprietary 'TSEMP') protocol
				2 = HMS protocol"
			::= { modemSettings 16 }

		
-- Transponder modem statistics objects.
		-- 1.3.6.1.4.1.3715.100.1.2
		modemStats OBJECT IDENTIFIER ::= { hmsModem 2 }

		
		-- 1.3.6.1.4.1.3715.100.1.2.2
		modemReceived OBJECT-TYPE
			SYNTAX INTEGER (1..65536)
			ACCESS read-only
			STATUS mandatory
			DESCRIPTION
				"Number of received packets (MAC + payload))"
			::= { modemStats 2 }

		
		-- 1.3.6.1.4.1.3715.100.1.2.3
		modemBad OBJECT-TYPE
			SYNTAX INTEGER (1..65536)
			ACCESS read-only
			STATUS mandatory
			DESCRIPTION
				"Number of received packets declared as bad."
			::= { modemStats 3 }

		
		-- 1.3.6.1.4.1.3715.100.1.2.4
		modemSent OBJECT-TYPE
			SYNTAX INTEGER (1..65536)
			ACCESS read-only
			STATUS mandatory
			DESCRIPTION
				"Number of sent packets."
			::= { modemStats 4 }

		
		-- 1.3.6.1.4.1.3715.100.1.2.5
		modemResetStat OBJECT-TYPE
			SYNTAX INTEGER { reset(1) }
			ACCESS read-write
			STATUS mandatory
			DESCRIPTION
				"Write only variable for resetting the modem packet
				statistics counters. A get always returna value 1."
			::= { modemStats 5 }

		
		-- 1.3.6.1.4.1.3715.100.1.3
		modemStatus OBJECT IDENTIFIER ::= { hmsModem 3 }

		
		-- 1.3.6.1.4.1.3715.100.1.3.1
		modemStatusRxLevel OBJECT-TYPE
			SYNTAX ValueStatus
			ACCESS read-only
			STATUS mandatory
			DESCRIPTION
				"Status of modem receive level:
				1 = normal
				2 = HIHI
				3 = HI
				4 = LO
				5 = LOLO"
			::= { modemStatus 1 }

		
	
	END

--
-- TELESTE-HMSMODEM-MIB.mib
--
