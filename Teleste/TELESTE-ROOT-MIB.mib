--
-- TELESTE-ROOT-MIB.mib
-- MIB generated by MG-SOFT Visual MIB Builder 2023 (64-bit) Version 16.00  Build 1600
-- Thursday, April 27, 2023 at 09:19:23
--

-- *****************************************************************************
-- Copyright (c) 2000-2020 by:
-- 
-- Teleste Corporation
-- Telestenkatu 1
-- FI-20660 Littoinen, Finland
-- tel. +358 2 2605 611
-- url: http://www.teleste.com
-- 
-- Description: Root module for Teleste enterprise MIBs
-- 
-- Revision history:
-- -----------------
-- 89, 27.4.2023 Sami Kuusisto
-- - Added dcc root (1.3.6.1.4.1.3715.51).
-- 
-- 88, 21.5.2021 Sami Kuusisto
-- - Added functional/trapReceivers (1.3.6.1.4.1.3715.100.105).
-- 
-- 87, 1.2.2021 Sami Kuusisto
-- - Added functional/network (1.3.6.1.4.1.3715.100.104).
-- 
-- 86, 4.2.2020 Matti Susi
-- - Added RIS root/product family (1.3.6.1.4.1.3715.50).
-- 
-- 85, 28.11.2018 Sami Kuusisto
-- - Added OFA root/product family (1.3.6.1.4.1.3715.21).
-- 
-- 84, 7.11.2017, Sami Kuusisto
-- - Added ICON product family (1.3.6.1.4.1.3715.20).
-- 
-- 83, 21.2.2017, Sami Kuusisto
-- - Added rpd (1.3.6.1.4.1.3715.100.103).
-- 
-- 82, 2.12.2016, Sami Kuusisto
-- - Added functions (1.3.6.1.4.1.3715.100.102).
-- 
-- 81, 9.1.2015, Sami Kuusisto
-- - Added temperature (1.3.6.1.4.1.3715.100.95).
-- 
-- 80, 8.12.2014, Sami Kuusisto
-- - Added packetStatistics (1.3.6.1.4.1.3715.100.97) and ipSettings (1.3.6.1.4.1.3715.100.98).
-- 
-- 79, 17.11.2014, Matti Susi
-- - Renamed ETTH to DAx.
-- 
-- 78, 26.3.2014, Sami Kuusisto
-- - Renamed transponderSetButton to automaticAlignmentButton.
-- 
-- 77, 13.3.2014 Sami Kuusisto
-- - added ACE and a lot of functional interfaces.
-- 
-- 76, 14.8.2012 Sami Halen
-- - added Optimo root
-- 
-- 75, 26.1.2012 Sami Halen
-- - moved cmConfig functional subgroup to end of functional group (.3715.100.7 => .3715.100.999)
-- 
-- 74, 10.1.2012 Sami Halen
-- - added functional subgroups previously defined only in respective MIBs: 
--   - alarms
--   - cmConfig
--   - levelManagement
--   - heStatus
--   - trapControl
--   - from hfcOptics:
--     - opticalTransmitter
--     - opticalReceiver
--     - opticalAmplifier
--     - rfAmplifier
-- - heStatus moved from functional.1 to functional.21 to prevent overlap with hmsModem
-- 
-- 1.73 16.12.2009 Rainer Salminen and Sami Salo
-- - added cxx root
-- 
-- 1.72, 26.2.2009 Matti Susi
-- - added hmts functional group
-- 
-- 1.71, 20.2.2009 Matti Susi
-- - added ntpcontrol functional group
-- - added Luminato root
-- 
-- 1.70, 26.3.2008 Matti Susi
-- - added pilotGenerator functional group
-- 
-- 1.69, 11.1.2008 Matti Susi
-- - added FTTH root
-- 
-- 1.68, 26.4.2007 Matti Susi
-- - added spectrum analyser functional group
-- 
-- 1.67, 12.4.2006 Matti Susi
-- - added ValueStatus type assignment
-- 
-- 1.66, 8.12.2005 Matti Susi
-- - moved functional group definitions up from functional MIBs
-- 
-- 1.65, 25.11.2005 Matti Susi
-- - added CFO root
-- 
-- 1.64, 11.8.2005 Matti Susi
-- - added HDO root
-- 
-- 1.63, 12.11.2004 Matti Susi
-- - added EttH root
-- 
-- 1.62, 17.3.2004 Matti Susi
-- - object groups functional and experimental added
-- 
-- 1.61, 2.4.2003 Matti Susi
-- - added ACx root
-- 
-- 1.6, 12.12.2002 Matti Susi
-- - object groups 'functional' and experimental' moved to
--   TELESTE-ROOT2-MIB
-- 
-- 1.5, 14.10.2002 Matti Susi
-- - object groups 'functional' and experimental' added
-- - recommended syntax fo DateAndTime changed
-- 
-- 1.4, 14.8.2002 Matti Susi
-- - added EMT root
-- 
-- 1.3, 02.07.2002 Pasi Pöri
-- - added EASI root
--  
-- 1.2, 05.11.2001 Rainer Salminen
-- - changed the base type of DateAndTime 
--   from Octetstring to DisplayString
-- 
-- 1.1, 24.10.2001 Rainer Salminen
-- - changed length of DateAndTime to 16..28
-- - added rules about DateAndTime format
-- 
-- 1.0, 11.10.2001 Rainer Salminen
-- - first official release
-- - section gendata deprecated
-- - added section common(99) to replace gendata
-- 
-- ****************************************************************************
-- 

	TELESTE-ROOT-MIB DEFINITIONS ::= BEGIN
 
		IMPORTS
			enterprises			
				FROM RFC1155-SMI			
			DisplayString			
				FROM RFC1213-MIB;
	
	
--
-- Type definitions
--
	
		TDisplayString ::= OCTET STRING (SIZE (0..255))

		TPhysAddress ::= OCTET STRING (SIZE (6))

		Int8 ::= INTEGER (-128..127)

		Int16 ::= INTEGER (-32768..32768)

		Uint8 ::= INTEGER (0..255)

		Uint16 ::= INTEGER (0..65536)

		Uint32 ::= INTEGER (0..2147483647)

-- A date-time specification. It is recommended to follow
-- the syntax in SNMPv2-TC MIB (RFC2579), as follows:
-- 
--     field  octets  contents                  range
--     -----  ------  --------                  -----
--       1      1-2   year                      0..65536
--       2       3    month                     1..12
--       3       4    day                       1..31
--       4       5    hour                      0..23
--       5       6    minutes                   0..59
--       6       7    seconds                   0..60
--                    (use 60 for leap-second)
--       7       8    deci-seconds              0..9
--       8       9    direction from UTC        '+' / '-'
--       9      10    hours from UTC            0..11
--      10      11    minutes from UTC          0..59
--  	
--      For example, Tuesday May 26, 1992 at 1:30:15 PM EDT would be
--      displayed as:
--  	
--           1992-5-26,13:30:15.0,-4:0
-- 	
--      Note that if only local time is known, then timezone
--      information (fields 8-10) is not present.
-- 
-- -------------------------------------------------------------
-- This is the original description not recommended for new
-- agent designs:
-- 
-- Date and time is represented in extended ISO time format:
-- 
--        CCYY-MM-DD HH:MM[:SS.ss][Zone]
-- 
-- Items in brackets are optional. 
-- Zone is a character 'Z' for UTC-time or offset to UTC-time
-- in format +hh:mm or -hh:mm.
-- 
		DateAndTime ::= DisplayString (SIZE (16..28))

-- 'HMS style' value definition for status objects.
		ValueStatus ::= INTEGER
			{
			valueNormal(1),
			valueHIHI(2),
			valueHi(3),
			valueLo(4),
			valueLOLO(5)
			}

	
--
-- Node definitions
--
	
-- TELESTE root object identifier
		-- 1.3.6.1.4.1.3715
		teleste OBJECT IDENTIFIER ::= { enterprises 3715 }

		
-- EMS server objects (SNMP Wizard)
		-- 1.3.6.1.4.1.3715.1
		ems OBJECT IDENTIFIER ::= { teleste 1 }

		
-- Objects common to all teleste products/agents.
-- Deprecated 11.10.2001 and replaced with section Common.
		-- 1.3.6.1.4.1.3715.2
		gendata OBJECT IDENTIFIER ::= { teleste 2 }

		
-- BK product family specific objects
		-- 1.3.6.1.4.1.3715.3
		bk OBJECT IDENTIFIER ::= { teleste 3 }

		
-- BXX product family specific objects
		-- 1.3.6.1.4.1.3715.4
		bxx OBJECT IDENTIFIER ::= { teleste 4 }

		
-- DVO product family specific objects
		-- 1.3.6.1.4.1.3715.5
		dvo OBJECT IDENTIFIER ::= { teleste 5 }

		
-- DVX product family specific objects
		-- 1.3.6.1.4.1.3715.6
		dvx OBJECT IDENTIFIER ::= { teleste 6 }

		
-- INF product family specific objects
		-- 1.3.6.1.4.1.3715.7
		inf OBJECT IDENTIFIER ::= { teleste 7 }

		
-- ATMux product family specific objects
		-- 1.3.6.1.4.1.3715.8
		atmux OBJECT IDENTIFIER ::= { teleste 8 }

		
-- Edge Access System Interface product family specific objects
		-- 1.3.6.1.4.1.3715.9
		easi OBJECT IDENTIFIER ::= { teleste 9 }

		
-- EMT product family specific objects
		-- 1.3.6.1.4.1.3715.10
		emt OBJECT IDENTIFIER ::= { teleste 10 }

		
-- ACx product family specific objects
		-- 1.3.6.1.4.1.3715.11
		acx OBJECT IDENTIFIER ::= { teleste 11 }

		
-- ACE series specific objects
		-- 1.3.6.1.4.1.3715.11.579
		ace OBJECT IDENTIFIER ::= { acx 579 }

		
-- DAx product family specific objects. Used to be ETTH.
		-- 1.3.6.1.4.1.3715.12
		dax OBJECT IDENTIFIER ::= { teleste 12 }

		
-- HDO product family specific objects
		-- 1.3.6.1.4.1.3715.14
		hdo OBJECT IDENTIFIER ::= { teleste 14 }

		
-- CFO product family specific objects
		-- 1.3.6.1.4.1.3715.15
		cfo OBJECT IDENTIFIER ::= { teleste 15 }

		
-- FTTH product family specific objects
		-- 1.3.6.1.4.1.3715.16
		ftth OBJECT IDENTIFIER ::= { teleste 16 }

		
-- Luminato product family specific objects
		-- 1.3.6.1.4.1.3715.17
		luminato OBJECT IDENTIFIER ::= { teleste 17 }

		
-- CXX product family specific objects
		-- 1.3.6.1.4.1.3715.18
		cxx OBJECT IDENTIFIER ::= { teleste 18 }

		
-- Optimo product family specific objects
		-- 1.3.6.1.4.1.3715.19
		optimo OBJECT IDENTIFIER ::= { teleste 19 }

		
-- ICON product family specific objects
		-- 1.3.6.1.4.1.3715.20
		icon OBJECT IDENTIFIER ::= { teleste 20 }

		
-- OFA product family
		-- 1.3.6.1.4.1.3715.21
		ofa OBJECT IDENTIFIER ::= { teleste 21 }

		
-- Rail Information Solutions (RIS) root OID
		-- 1.3.6.1.4.1.3715.50
		ris OBJECT IDENTIFIER ::= { teleste 50 }

		
-- Display Competence Center (DCC) root OID.
		-- 1.3.6.1.4.1.3715.51
		dcc OBJECT IDENTIFIER ::= { teleste 51 }

		
-- Objects common to all Teleste products
		-- 1.3.6.1.4.1.3715.99
		common OBJECT IDENTIFIER ::= { teleste 99 }

		
-- Functional object groups
		-- 1.3.6.1.4.1.3715.100
		functional OBJECT IDENTIFIER ::= { teleste 100 }

		
		-- 1.3.6.1.4.1.3715.100.1
		hmsModem OBJECT IDENTIFIER ::= { functional 1 }

		
		-- 1.3.6.1.4.1.3715.100.2
		spectrumAnalyser OBJECT IDENTIFIER ::= { functional 2 }

		
		-- 1.3.6.1.4.1.3715.100.3
		pilotGenerator OBJECT IDENTIFIER ::= { functional 3 }

		
		-- 1.3.6.1.4.1.3715.100.4
		ntpcontrol OBJECT IDENTIFIER ::= { functional 4 }

		
		-- 1.3.6.1.4.1.3715.100.5
		hmts OBJECT IDENTIFIER ::= { functional 5 }

		
		-- 1.3.6.1.4.1.3715.100.6
		levelManagement OBJECT IDENTIFIER ::= { functional 6 }

		
		-- 1.3.6.1.4.1.3715.100.7
		commonModem OBJECT IDENTIFIER ::= { functional 7 }

		
		-- 1.3.6.1.4.1.3715.100.8
		catvisorModem OBJECT IDENTIFIER ::= { functional 8 }

		
		-- 1.3.6.1.4.1.3715.100.10
		hfcOptics OBJECT IDENTIFIER ::= { functional 10 }

		
		-- 1.3.6.1.4.1.3715.100.11
		opticalTransmitter OBJECT IDENTIFIER ::= { functional 11 }

		
		-- 1.3.6.1.4.1.3715.100.12
		opticalReceiver OBJECT IDENTIFIER ::= { functional 12 }

		
		-- 1.3.6.1.4.1.3715.100.13
		opticalAmplifier OBJECT IDENTIFIER ::= { functional 13 }

		
		-- 1.3.6.1.4.1.3715.100.14
		rfAmplifier OBJECT IDENTIFIER ::= { functional 14 }

		
		-- 1.3.6.1.4.1.3715.100.20
		headEnd OBJECT IDENTIFIER ::= { functional 20 }

		
		-- 1.3.6.1.4.1.3715.100.21
		heStatus OBJECT IDENTIFIER ::= { functional 21 }

		
		-- 1.3.6.1.4.1.3715.100.41
		amplifierForwardPath OBJECT IDENTIFIER ::= { functional 41 }

		
		-- 1.3.6.1.4.1.3715.100.43
		nodeForwardPath OBJECT IDENTIFIER ::= { functional 43 }

		
		-- 1.3.6.1.4.1.3715.100.45
		opticalForwardTransmitter OBJECT IDENTIFIER ::= { functional 45 }

		
		-- 1.3.6.1.4.1.3715.100.47
		opticalForwardReceiver OBJECT IDENTIFIER ::= { functional 47 }

		
		-- 1.3.6.1.4.1.3715.100.51
		amplifierReturnPath OBJECT IDENTIFIER ::= { functional 51 }

		
		-- 1.3.6.1.4.1.3715.100.53
		nodeReturnPath OBJECT IDENTIFIER ::= { functional 53 }

		
		-- 1.3.6.1.4.1.3715.100.55
		opticalReturnTransmitter OBJECT IDENTIFIER ::= { functional 55 }

		
		-- 1.3.6.1.4.1.3715.100.57
		opticalReturnReceiver OBJECT IDENTIFIER ::= { functional 57 }

		
		-- 1.3.6.1.4.1.3715.100.59
		digitalReturnTransmitter OBJECT IDENTIFIER ::= { functional 59 }

		
		-- 1.3.6.1.4.1.3715.100.61
		ingressSwitch OBJECT IDENTIFIER ::= { functional 61 }

		
		-- 1.3.6.1.4.1.3715.100.71
		levelControl OBJECT IDENTIFIER ::= { functional 71 }

		
		-- 1.3.6.1.4.1.3715.100.73
		levelDetector OBJECT IDENTIFIER ::= { functional 73 }

		
		-- 1.3.6.1.4.1.3715.100.75
		alsc OBJECT IDENTIFIER ::= { functional 75 }

		
		-- 1.3.6.1.4.1.3715.100.82
		omiBasedAlignment OBJECT IDENTIFIER ::= { functional 82 }

		
		-- 1.3.6.1.4.1.3715.100.84
		pilotBasedAlignment OBJECT IDENTIFIER ::= { functional 84 }

		
		-- 1.3.6.1.4.1.3715.100.92
		performance OBJECT IDENTIFIER ::= { functional 92 }

		
		-- 1.3.6.1.4.1.3715.100.94
		automaticAlignmentButton OBJECT IDENTIFIER ::= { functional 94 }

		
		-- 1.3.6.1.4.1.3715.100.95
		temperature OBJECT IDENTIFIER ::= { functional 95 }

		
		-- 1.3.6.1.4.1.3715.100.96
		accessories OBJECT IDENTIFIER ::= { functional 96 }

		
		-- 1.3.6.1.4.1.3715.100.97
		packetStatistics OBJECT IDENTIFIER ::= { functional 97 }

		
		-- 1.3.6.1.4.1.3715.100.98
		ipSettings OBJECT IDENTIFIER ::= { functional 98 }

		
		-- 1.3.6.1.4.1.3715.100.99
		module OBJECT IDENTIFIER ::= { functional 99 }

		
		-- 1.3.6.1.4.1.3715.100.100
		alarms OBJECT IDENTIFIER ::= { functional 100 }

		
		-- 1.3.6.1.4.1.3715.100.101
		trapControl OBJECT IDENTIFIER ::= { functional 101 }

		
		-- 1.3.6.1.4.1.3715.100.102
		functions OBJECT IDENTIFIER ::= { functional 102 }

		
		-- 1.3.6.1.4.1.3715.100.103
		rpd OBJECT IDENTIFIER ::= { functional 103 }

		
		-- 1.3.6.1.4.1.3715.100.104
		network OBJECT IDENTIFIER ::= { functional 104 }

		
		-- 1.3.6.1.4.1.3715.100.105
		trapReveicers OBJECT IDENTIFIER ::= { functional 105 }

		
		-- 1.3.6.1.4.1.3715.100.999
		cmConfig OBJECT IDENTIFIER ::= { functional 999 }

		
-- Placeholder for experimental and preliminary MIB modules
		-- 1.3.6.1.4.1.3715.999
		experimental OBJECT IDENTIFIER ::= { teleste 999 }

		
	
	END

--
-- TELESTE-ROOT-MIB.mib
--
