--
-- TELESTE-FUNCTIONAL-OMI-BASED-ALIGNMENT-MIB.mib
-- MIB generated by MG-SOFT Visual MIB Builder 2013 (64-bit) Version 9.0  Build 760
-- Thursday, June 05, 2014 at 14:03:48
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-OMI-BASED-ALIGNMENT-MIB
-- 
-- Description:   MIB module describing Teleste functional omi based alignment interface specific objects
-- 
-- Revision history:
-- -----------------
-- 3, 5.6.2014, Sami Kuusisto
-- - Added value ranges.
-- 
-- 2, 13.3.2014, Sami Kuusisto
-- - added omiBasedAlignmentTargetOmi and omiBasedAlignmentTargetLevel
-- 
-- 1, 10.3.2014, Sami Kuusisto
-- - Initial version.
-- 
-- ****************************************************************************
-- 

	TELESTE-FUNCTIONAL-OMI-BASED-ALIGNMENT-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.82
		omiBasedAlignment OBJECT IDENTIFIER ::= { functional 82 }

		
		-- 1.3.6.1.4.1.3715.100.82.1
		omiBasedAlignmentTable OBJECT-TYPE
			SYNTAX SEQUENCE OF OmiBasedAlignmentEntry
			ACCESS not-accessible
			STATUS mandatory
			DESCRIPTION
				"A table of OMI based alignment settings."
			::= { omiBasedAlignment 1 }

		
		-- 1.3.6.1.4.1.3715.100.82.1.1
		omiBasedAlignmentEntry OBJECT-TYPE
			SYNTAX OmiBasedAlignmentEntry
			ACCESS not-accessible
			STATUS mandatory
			INDEX { functionalModuleId }
			::= { omiBasedAlignmentTable 1 }

		
		OmiBasedAlignmentEntry ::=
			SEQUENCE { 
				omiBasedAlignmentStart
					INTEGER,
				omiBasedAlignmentStatus
					INTEGER,
				omiBasedAlignmentTargetOmi
					INTEGER,
				omiBasedAlignmentTargetLevel
					INTEGER
			 }

		-- 1.3.6.1.4.1.3715.100.82.1.1.1
		omiBasedAlignmentStart OBJECT-TYPE
			SYNTAX INTEGER
				{
				omiBasedAlignmentStart(1),
				omiBasedAlignmentStartWriteOnly(2)
				}
			ACCESS read-write
			STATUS mandatory
			DESCRIPTION
				"Start pilot based alignment procedure.
				1: start alignment.
				2: reply when reading this object."
			::= { omiBasedAlignmentEntry 1 }

		
		-- 1.3.6.1.4.1.3715.100.82.1.1.2
		omiBasedAlignmentStatus OBJECT-TYPE
			SYNTAX INTEGER
				{
				omiBasedAlignmentStatusNeverRun(1),
				omiBasedAlignmentStatusRunning(2),
				omiBasedAlignmentStatusSuccess(3),
				omiBasedAlignmentStatusNoTunerModule(4),
				omiBasedAlignmentStatusTargetsOutOfRange(5),
				omiBasedAlignmentStatusInterStageSlopeOufOfRange(6),
				omiBasedAlignmentStatusPilotsNotFound(7),
				omiBasedAlignmentStatusInputSlopeOutOfRange(8),
				omiBasedAlignmentStatusGainTargetOutOfRange(9),
				omiBasedAlignmentStatusCableSimulatorNeeded(10),
				omiBasedAlignmentStatusGainOrSlopeSaturated(11),
				omiBasedAlignmentStatusUnknownForwardPathPlug(12),
				omiBasedAlignmentStatusGain2TargetOutOfRange(13),
				omiBasedAlignmentStatusInterStage2SlopeOutOfRange(14),
				omiBasedAlignmentStatusOpticalInputPowerOutOfRange(15),
				omiBasedAlignmentStatusWaitingForRun(16),
				omiBasedAlignmentStatusCanceled(17)
				}
			ACCESS read-only
			STATUS mandatory
			DESCRIPTION
				"Status of last omi based automatic aligment:
				 	1 = never run
				 	2 = running
				 	3 = success
				 	4 = no tuner module
				 	5 = targets out of range
				 	6 = interstage slope target ouf of range
				 	7 = pilots not found
				 	8 = input slope out of range
				 	9 = gain target out of range
				 	10 = a cable simulator may be needed into the universal plug-in slot
				 	11 = gain or slope is saturated
				 	12 = unknown forward path plug-in module
				 	13 = alignGain2TargetOutOfRange
				 	14 = alignInterStage2SlopeOutOfRange
				 	15 = alignOpticalInputPowerOutOfRange
				 	16 = alignWaitingForRun
				 	17 = alignCanceled"
			::= { omiBasedAlignmentEntry 2 }

		
		-- 1.3.6.1.4.1.3715.100.82.1.1.3
		omiBasedAlignmentTargetOmi OBJECT-TYPE
			SYNTAX INTEGER (0..10000)
			ACCESS read-write
			STATUS mandatory
			DESCRIPTION
				"Target OMI.
				Unit 0.01 %."
			::= { omiBasedAlignmentEntry 3 }

		
		-- 1.3.6.1.4.1.3715.100.82.1.1.4
		omiBasedAlignmentTargetLevel OBJECT-TYPE
			SYNTAX INTEGER (0..20000)
			ACCESS read-write
			STATUS mandatory
			DESCRIPTION
				"Target level.
				Unit 0.01 dBµV."
			::= { omiBasedAlignmentEntry 4 }

		
	
	END

--
-- TELESTE-FUNCTIONAL-OMI-BASED-ALIGNMENT-MIB.mib
--
