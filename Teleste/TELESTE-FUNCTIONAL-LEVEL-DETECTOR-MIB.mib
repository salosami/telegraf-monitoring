--
-- TELESTE-FUNCTIONAL-LEVEL-DETECTOR-MIB.mib
-- MIB generated by MG-SOFT Visual MIB Builder 2023 (64-bit) Version 16.00  Build 1600
-- Wednesday, April 05, 2023 at 08:13:27
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-LEVEL-DETECTOR-MIB
-- 
-- Description:   MIB module describing Teleste functional level detector interface specific objects
-- 
-- Revision history:
-- -----------------
-- 6, 5.4.2023, Sami Kuusisto
-- - Added TCP to usage and mode.
-- 
-- 5, 14.2.2019, Sami Kuusisto
-- - Added levelDetectorSupportedModes.
-- 
-- 4, 13.2.2019, Sami Kuusisto
-- - Added new enums 6 and 7 to levelDetectorMode.
-- 
-- 3, 21.1.2019, Sami Kuusisto
-- - Added new enums 4, 5 and 16 to levelDetectorMode.
-- 
-- 2, 5.6.2014, Sami Kuusisto
-- - Added value ranges.
-- 
-- 1, 10.3.2014, Sami Kuusisto
-- - Initial version.
-- 
-- ****************************************************************************
-- 

	TELESTE-FUNCTIONAL-LEVEL-DETECTOR-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.73
		levelDetector OBJECT IDENTIFIER ::= { functional 73 }

		
		-- 1.3.6.1.4.1.3715.100.73.1
		levelDetectorTable OBJECT-TYPE
			SYNTAX SEQUENCE OF LevelDetectorEntry
			ACCESS not-accessible
			STATUS mandatory
			DESCRIPTION
				"A table of level detector entries."
			::= { levelDetector 1 }

		
		-- 1.3.6.1.4.1.3715.100.73.1.1
		levelDetectorEntry OBJECT-TYPE
			SYNTAX LevelDetectorEntry
			ACCESS not-accessible
			STATUS mandatory
			INDEX { functionalModuleId }
			::= { levelDetectorTable 1 }

		
		LevelDetectorEntry ::=
			SEQUENCE { 
				levelDetectorFrequency
					INTEGER,
				levelDetectorUsage
					INTEGER,
				levelDetectorMode
					INTEGER,
				levelDetectorValue
					INTEGER,
				levelDetectorLostLevel
					INTEGER,
				levelDetectorStatus
					INTEGER,
				levelDetectorSupportedModes
					INTEGER
			 }

		-- 1.3.6.1.4.1.3715.100.73.1.1.1
		levelDetectorFrequency OBJECT-TYPE
			SYNTAX INTEGER (0..2000000)
			ACCESS read-write
			STATUS mandatory
			DESCRIPTION
				"Level detector frequency. Unit 1 kHz.
				0 = Wideband detector (read-only)."
			::= { levelDetectorEntry 1 }

		
		-- 1.3.6.1.4.1.3715.100.73.1.1.2
		levelDetectorUsage OBJECT-TYPE
			SYNTAX INTEGER
				{
				other(1),
				pilotHighMain(2),
				pilotHighReserve(3),
				pilotLowMain(4),
				pilotLowReserve(5),
				monitorSignal(6),
				monitorWideband(7),
				totalPower(8),
				tcp(9)
				}
			ACCESS read-only
			STATUS mandatory
			DESCRIPTION
				"Use of the level measurement:
				1 = Other
				2 = Main high pilot
				3 = Reserve high pilot
				4 = Main low pilot
				5 = Reserve low pilot
				6 = Signal monitor
				7 = Wideband signal monitor
				8 = Total power
				9 = TCP
				
				Target levels exist only for entry types 2...5."
			::= { levelDetectorEntry 2 }

		
		-- 1.3.6.1.4.1.3715.100.73.1.1.3
		levelDetectorMode OBJECT-TYPE
			SYNTAX INTEGER
				{
				modeAnalog(1),
				modeQam(2),
				modeWideband(3),
				modeAnnexB(4),
				modeOFDM(5),
				modeMinHold(6),
				modeMaxHold(7),
				modeTcp(8),
				modeUnset(16)
				}
			ACCESS read-write
			STATUS mandatory
			DESCRIPTION
				"Level detector operating mode:
				1 = peak hold for analogue TV channel or carrier (pilot)
				2 = average for QAM (EU)/AnnexA (6.875 MHz) channel or noise
				3 = wideband signal power monitor (read only)
				4 = average for QAM (US)/AnnexB (5.4 MHz) channel
				5 = average for QFDM (6.0 MHz) channel
				6 = minHold
				7 = maxHold
				8 = TCP
				16 = operating mode is not set or is unknown.
				"
			::= { levelDetectorEntry 3 }

		
		-- 1.3.6.1.4.1.3715.100.73.1.1.4
		levelDetectorValue OBJECT-TYPE
			SYNTAX INTEGER (0..20000)
			ACCESS read-only
			STATUS mandatory
			DESCRIPTION
				"Measured signal level. Unit 0.01 dBµV (dB for wideband signal monitor)."
			::= { levelDetectorEntry 4 }

		
		-- 1.3.6.1.4.1.3715.100.73.1.1.5
		levelDetectorLostLevel OBJECT-TYPE
			SYNTAX INTEGER (0..20000)
			ACCESS read-write
			STATUS mandatory
			DESCRIPTION
				"A level value below which the signal is declared as 'lost'.
				Unit 0.01 dBµV."
			::= { levelDetectorEntry 5 }

		
		-- 1.3.6.1.4.1.3715.100.73.1.1.6
		levelDetectorStatus OBJECT-TYPE
			SYNTAX INTEGER
			ACCESS read-write
			STATUS mandatory
			DESCRIPTION
				"Pilot status (bitfield)
				0x0001: pilot ok (this is set only if all others are reset)
				0x0002: pilot disabled (by user)
				0x0004: pilot disabled (by esw; no transponder)
				0x0008: reserved
				0x0010: pilot below pilot lost decision level (= pilot lost)
				0x0020: reserved, 0x0040: reserved, 0x0080: reserved
				0x0100: illegal pilot frequency (too low or too high)
				0x0200: pilot measurement result error (= too high measurement)
				0x0400: hardware error
				0x0800: reserved, 
				0x1000: reserved, 
				0x2000: reserved, 
				0x4000: reserved, 
				0x8000: reserved"
			::= { levelDetectorEntry 6 }

		
		-- 1.3.6.1.4.1.3715.100.73.1.1.7
		levelDetectorSupportedModes OBJECT-TYPE
			SYNTAX INTEGER
			ACCESS read-only
			STATUS mandatory
			DESCRIPTION
				"Supported levelDetectorModes. This is bitfield.
				
				0x01: Legacy analog and digital/AnnexA/EU QAM supported.
				0x02: Annex B/US QAM and OFDM supported.
				0x04: MinHold and MaxHold supported.
				
				NOTE! TCP measurement reports 0 to this OID."
			::= { levelDetectorEntry 7 }

		
	
	END

--
-- TELESTE-FUNCTIONAL-LEVEL-DETECTOR-MIB.mib
--
