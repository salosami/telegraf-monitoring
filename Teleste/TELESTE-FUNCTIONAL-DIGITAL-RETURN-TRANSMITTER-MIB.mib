--
-- TELESTE-FUNCTIONAL-DIGITAL-RETURN-TRANSMITTER-MIB.mib
-- MIB generated by MG-SOFT Visual MIB Builder 2013 (64-bit) Version 9.0  Build 760
-- Wednesday, March 12, 2014 at 13:30:35
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-DIGITAL-RETURN-TRANSMITTER-MIB
-- 
-- Description:   MIB module describing Teleste functional digital return transmitter interface specific objects
-- 
-- Revision history:
-- -----------------
-- 1, 11.3.2014, Sami Kuusisto
-- - Initial version.
-- 
-- ****************************************************************************
-- 

	TELESTE-FUNCTIONAL-DIGITAL-RETURN-TRANSMITTER-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.59
		digitalReturnTransmitter OBJECT IDENTIFIER ::= { functional 59 }

		
		-- 1.3.6.1.4.1.3715.100.59.1
		digitalReturnTransmitterTable OBJECT-TYPE
			SYNTAX SEQUENCE OF DigitalReturnTransmitterEntry
			ACCESS not-accessible
			STATUS mandatory
			DESCRIPTION
				"A table of return transmitter control entries."
			::= { digitalReturnTransmitter 1 }

		
		-- 1.3.6.1.4.1.3715.100.59.1.1
		digitalReturnTransmitterEntry OBJECT-TYPE
			SYNTAX DigitalReturnTransmitterEntry
			ACCESS not-accessible
			STATUS mandatory
			INDEX { functionalModuleId }
			::= { digitalReturnTransmitterTable 1 }

		
		DigitalReturnTransmitterEntry ::=
			SEQUENCE { 
				digitalReturnTransmitterRfLevel
					INTEGER
			 }

		-- 1.3.6.1.4.1.3715.100.59.1.1.1
		digitalReturnTransmitterRfLevel OBJECT-TYPE
			SYNTAX INTEGER
			ACCESS read-only
			STATUS mandatory
			DESCRIPTION
				"Return transmitter RF input level. 
				Unit 0.01 dB."
			::= { digitalReturnTransmitterEntry 1 }

		
	
	END

--
-- TELESTE-FUNCTIONAL-DIGITAL-RETURN-TRANSMITTER-MIB.mib
--
