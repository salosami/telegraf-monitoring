--
-- TELESTE-HMTS-MIB.mib
-- MIB generated by MG-SOFT Visual MIB Builder 2013 (64-bit) Version 9.0  Build 760
-- Wednesday, May 04, 2016 at 10:59:23
--

-- ****************************************************************************
-- Copyright (c) 2009-2013 by:
-- 
-- Teleste Corporation
-- Seponkatu 1
-- FIN-20660 Littoinen, Finland
-- tel. +358 2 2605 611
-- url: http://www.teleste.com
-- 
-- Module Name: TELESTE-HMTS-MIB
-- 
-- Description: Teleste HMTS MIB extensions to HMS-HMTS MIB
-- 
-- Revision History:
-- -----------------
-- 4, 4.5.2016, Sami Kuusisto
-- - Added hmtsHfcErrorRate and hmtsHfcErrorRateTolerance.
-- 
-- 3, 25.4.2013, Sami Halen
-- - reversed order of hmtsDeviceStatus objects to { hmtsDevComStat, hmtsDevIPAddr }
-- 
-- 2,  7.11.2012, Matti Susi
-- - added hmtsDeviceStatus notification
-- - added hmtsHfcPatchOperation
-- 
-- 1,  12.4.2010, Matti Susi
-- - Corrected a typing error in basicCompliance
-- 
-- 0,  2.3.2010, Matti Susi
-- - First offcial release
-- 
-- ****************************************************************************

	TELESTE-HMTS-MIB DEFINITIONS ::= BEGIN
 
		IMPORTS
			hmtsDevPhysAddr, hmtsDevIPAddr, hmtsDevComStat			
				FROM SCTE-HMS-HMTS-MIB			
			OBJECT-GROUP, MODULE-COMPLIANCE, NOTIFICATION-GROUP			
				FROM SNMPv2-CONF			
			IpAddress, Integer32, OBJECT-TYPE, MODULE-IDENTITY, NOTIFICATION-TYPE			
				FROM SNMPv2-SMI			
			hmts			
				FROM TELESTE-ROOT-MIB;
	
	
		-- 1.3.6.1.4.1.3715.100.5.1
		hmtsMIB MODULE-IDENTITY 
			LAST-UPDATED "200905040952Z"		-- May 04, 2009 at 09:52 GMT
			ORGANIZATION 
				"Teleste Corporation"
			CONTACT-INFO 
				"Your contact info"
			DESCRIPTION 
				"MIB module for Teleste HMTS devices. Contains objects not available in
				SCTE-HMS-HMTS-MIB."
			::= { hmts 1 }

		
	
	
--
-- Node definitions
--
	
		-- 1.3.6.1.4.1.3715.100.5.1.1
		hmtsContModeBroadcastInterval OBJECT-TYPE
			SYNTAX INTEGER (1..600)
			UNITS "1 second"
			MAX-ACCESS read-write
			STATUS current
			DESCRIPTION
				"The interval of CONTMODE(ON) broadcasts in Contention mode."
			::= { hmtsMIB 1 }

		
		-- 1.3.6.1.4.1.3715.100.5.1.2
		hmtsNotRespondingThreshold OBJECT-TYPE
			SYNTAX INTEGER (1..100)
			MAX-ACCESS read-write
			STATUS current
			DESCRIPTION
				"The number of non-answered requests before the transponder
				is declared as 'not responding'."
			::= { hmtsMIB 2 }

		
		-- 1.3.6.1.4.1.3715.100.5.1.3
		hmtsHfcPollRoundTime OBJECT-TYPE
			SYNTAX Integer32
			UNITS "1 second"
			MAX-ACCESS read-only
			STATUS current
			DESCRIPTION
				"The time it takes to poll through all transponders in polling mode."
			::= { hmtsMIB 3 }

		
		-- 1.3.6.1.4.1.3715.100.5.1.5
		hmtsRegistrationStretchThreshold OBJECT-TYPE
			SYNTAX Integer32
			UNITS "percent"
			MAX-ACCESS read-write
			STATUS current
			DESCRIPTION
				"If a large number of transponders are registering at the same time, it
				may be necessary to extend the registration window. This object defines
				the threshold when this stretching should be performed. During registration,
				collisions are unavoidable, causing corrupted packets.
				By comparing the number of totally received bytes to the number of bytes
				belonging to correctly received packets can be used as an indicator.
				This object defines the threshold for this indicator. If the threshold is
				exceeded, the registration window duration is be doubles."
			::= { hmtsMIB 5 }

		
		-- 1.3.6.1.4.1.3715.100.5.1.8
		hmtsHfcPatchOperation OBJECT-TYPE
			SYNTAX OCTET STRING
			MAX-ACCESS read-write
			STATUS current
			DESCRIPTION
				"Get: Returns currently supported operations (bit field) 
				Example 01 06
				  0x01 : count of operation features bytes
				  0x06 : 0x02 = always high (this get operation supported)
				  0x04 = reset transponder counters operation supported (-> operation 0x02)
				  Tip: operation number can be solved by shifting bits toward BIT0.            
				
				Set values:
				  0x02 = resets HFC packet counters (Queries, Failures (%), Cont. failures)    
				
				"
			::= { hmtsMIB 8 }

		
		-- 1.3.6.1.4.1.3715.100.5.1.9
		hmtsDeviceStatus NOTIFICATION-TYPE
			OBJECTS { hmtsDevComStat, hmtsDevIPAddr }
			STATUS current
			DESCRIPTION 
				"This notification is sent every time a transponder's hmtsDevComStat value changes."
			::= { hmtsMIB 9 }

		
		-- 1.3.6.1.4.1.3715.100.5.1.10
		hmtsDeviceTable OBJECT-TYPE
			SYNTAX SEQUENCE OF HmtsDeviceEntry
			MAX-ACCESS not-accessible
			STATUS current
			DESCRIPTION
				"Extension objects to HMS-HMTS-MIB deviceTable."
			::= { hmtsMIB 10 }

		
		-- 1.3.6.1.4.1.3715.100.5.1.10.1
		hmtsDeviceEntry OBJECT-TYPE
			SYNTAX HmtsDeviceEntry
			MAX-ACCESS not-accessible
			STATUS current
			DESCRIPTION
				"Device table row definition."
			INDEX { hmtsDevPhysAddr }
			::= { hmtsDeviceTable 1 }

		
		HmtsDeviceEntry ::=
			SEQUENCE { 
				hmtsTransponderNEStatus
					Integer32
			 }

		-- 1.3.6.1.4.1.3715.100.5.1.10.1.1
		hmtsTransponderNEStatus OBJECT-TYPE
			SYNTAX Integer32
			MAX-ACCESS read-write
			STATUS current
			DESCRIPTION
				"Last commonNEStatus value read from the transponder."
			::= { hmtsDeviceEntry 1 }

		
		-- 1.3.6.1.4.1.3715.100.5.1.11
		hmtsTracing OBJECT IDENTIFIER ::= { hmtsMIB 11 }

		
		-- 1.3.6.1.4.1.3715.100.5.1.11.1
		trcServerAddress OBJECT-TYPE
			SYNTAX IpAddress
			MAX-ACCESS read-write
			STATUS current
			DESCRIPTION
				"SysLog server IP address."
			::= { hmtsTracing 1 }

		
		-- 1.3.6.1.4.1.3715.100.5.1.11.2
		trcBytes OBJECT-TYPE
			SYNTAX INTEGER
				{
				disable(1),
				enable(2)
				}
			MAX-ACCESS read-write
			STATUS current
			DESCRIPTION
				"Tracing of transmitted and received bytes."
			::= { hmtsTracing 2 }

		
		-- 1.3.6.1.4.1.3715.100.5.1.11.3
		trcPackets OBJECT-TYPE
			SYNTAX INTEGER
				{
				disable(1),
				enable(2)
				}
			MAX-ACCESS read-write
			STATUS current
			DESCRIPTION
				"Tracing of transmitted and received packets."
			::= { hmtsTracing 3 }

		
		-- 1.3.6.1.4.1.3715.100.5.1.11.4
		trcSnmp OBJECT-TYPE
			SYNTAX INTEGER
				{
				disable(1),
				enable(2)
				}
			MAX-ACCESS read-write
			STATUS current
			DESCRIPTION
				"Tracing of transmitted and received SNMP datagrams."
			::= { hmtsTracing 4 }

		
		-- 1.3.6.1.4.1.3715.100.5.1.12
		hmtsConformance OBJECT IDENTIFIER ::= { hmtsMIB 12 }

		
		-- 1.3.6.1.4.1.3715.100.5.1.12.1
		hmtsGroups OBJECT IDENTIFIER ::= { hmtsConformance 1 }

		
		-- 1.3.6.1.4.1.3715.100.5.1.12.1.1
		hmtsObjectGroup OBJECT-GROUP
			OBJECTS { hmtsContModeBroadcastInterval, hmtsNotRespondingThreshold, hmtsHfcPollRoundTime, hmtsRegistrationStretchThreshold, hmtsTransponderNEStatus, 
				trcServerAddress, trcBytes, trcPackets, trcSnmp, hmtsHfcPatchOperation
				 }
			STATUS current
			DESCRIPTION 
				"Teleste HMTS OBJECT-GROUP."
			::= { hmtsGroups 1 }

		
		-- 1.3.6.1.4.1.3715.100.5.1.12.1.2
		hmtsNotificationGroup NOTIFICATION-GROUP
			NOTIFICATIONS { hmtsDeviceStatus }
			STATUS current
			DESCRIPTION 
				"Description."
			::= { hmtsGroups 2 }

		
		-- 1.3.6.1.4.1.3715.100.5.1.12.2
		hmtsCompliances OBJECT IDENTIFIER ::= { hmtsConformance 2 }

		
		-- 1.3.6.1.4.1.3715.100.5.1.12.2.1
		basicCompliance MODULE-COMPLIANCE
			STATUS current
			DESCRIPTION 
				"Teleste HMTS MODULE-COMPLIANCE."
			MODULE -- this module
				MANDATORY-GROUPS { hmtsObjectGroup }
			::= { hmtsCompliances 1 }

		
		-- 1.3.6.1.4.1.3715.100.5.1.13
		hmtsHfcErrorRate OBJECT-TYPE
			SYNTAX Integer32 (0..100)
			UNITS "0.01 %"
			MAX-ACCESS read-write
			STATUS current
			DESCRIPTION
				"HFC error rate alarm value, which is highest transponder failure-%. 
				This value has analog alarm with user editable limits, defaults: HI=1%, HIHI=3%, deadband=0,5%. 
				User editable Tolerance parameter (hmtsErrorRateTolerance, default 0) allows ignoring worst X transponders. 
				Unit 0.01 %."
			::= { hmtsMIB 13 }

		
		-- 1.3.6.1.4.1.3715.100.5.1.14
		hmtsErrorRateTolerance OBJECT-TYPE
			SYNTAX Integer32
			UNITS "1 pcs"
			MAX-ACCESS read-write
			STATUS current
			DESCRIPTION
				"HFC error rate tolerance value allows ignoring worst X transponders. Used to control hmtsErrorRate related alarm. Unit 1 pcs (of transponders)."
			::= { hmtsMIB 14 }

		
	
	END

--
-- TELESTE-HMTS-MIB.mib
--
