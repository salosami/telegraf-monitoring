--
-- TELESTE-FUNCTIONAL-INGRESS-SWITCH-MIB.mib
-- MIB generated by MG-SOFT Visual MIB Builder 2018 (64-bit) Version 12.0  Build 1200
-- Tuesday, October 30, 2018 at 08:11:25
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-INGRESS-SWITCH-MIB
-- 
-- Description:   MIB module describing Teleste functional ingress switch interface specific objects
-- 
-- Revision history:
-- -----------------
-- 7, 30.10.2018, Sami Kuusisto
-- - Added new (RO) OID ingressSwitchControlModeVersion.
-- 
-- 6, 29.10.2018, Sami Kuusisto
-- - Added new enums (ingressSwitchControlModeAlarmOff(3) and ingressSwitchControlModeWarningAttenuateAlarmOff(4)) to ingressSwitchControlMode.
-- 
-- 5, 23.3.2016, Sami Kuusisto
-- - Changed ingressSwitchAttenuationStepSize, ingressSwitchAttenuationMinimumValue, ingressSwitchAttenuationMaximumValue as RO.
-- 
-- 4, 5.6.2014, Sami Kuusisto
-- - Added value ranges.
-- 
-- 3, 16.5.2014, Sami Kuusisto
-- - Added step size, step command, minimum and maximum values.
-- - Renumbered table childs.
-- 
-- 2, 14.3.2014, Sami Kuusisto
-- - Changed ingressSwitchMode enums to match SCTE enums.
-- 
-- 1, 10.3.2014, Sami Kuusisto
-- - Initial version.
-- 
-- ****************************************************************************
-- 

	TELESTE-FUNCTIONAL-INGRESS-SWITCH-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.61
		ingressSwitch OBJECT IDENTIFIER ::= { functional 61 }

		
-- A table of ingress switches.
		-- 1.3.6.1.4.1.3715.100.61.1
		ingressSwitchTable OBJECT-TYPE
			SYNTAX SEQUENCE OF IngressSwitchEntry
			ACCESS not-accessible
			STATUS mandatory
			DESCRIPTION
				"A table of ingress switches available in this device."
			::= { ingressSwitch 1 }

		
		-- 1.3.6.1.4.1.3715.100.61.1.1
		ingressSwitchEntry OBJECT-TYPE
			SYNTAX IngressSwitchEntry
			ACCESS not-accessible
			STATUS mandatory
			INDEX { functionalModuleId }
			::= { ingressSwitchTable 1 }

		
		IngressSwitchEntry ::=
			SEQUENCE { 
				ingressSwitchMode
					INTEGER,
				ingressSwitchAttenuation
					INTEGER,
				ingressSwitchAttenuationStepSize
					INTEGER,
				ingressSwitchAttenuationStep
					INTEGER,
				ingressSwitchAttenuationMinimumValue
					INTEGER,
				ingressSwitchAttenuationMaximumValue
					INTEGER,
				ingressSwitchControlMode
					INTEGER,
				ingressSwitchActivationDelay
					INTEGER,
				ingressSwitchDeActivationDelay
					INTEGER,
				ingressSwitchControlModeVersion
					INTEGER
			 }

		-- 1.3.6.1.4.1.3715.100.61.1.1.1
		ingressSwitchMode OBJECT-TYPE
			SYNTAX INTEGER
				{
				on(1),
				off(2),
				attenuated(3)
				}
			ACCESS read-write
			STATUS mandatory
			DESCRIPTION
				"Return path ingress switch state:
				1 = low/on (0 dB/no attenuation)
				2 = high/off (>45 dB/full attenuation/return path cut off)
				3 = attenuated (pad)
				
				This object has an entry in the discretePropertyTable."
			::= { ingressSwitchEntry 1 }

		
		-- 1.3.6.1.4.1.3715.100.61.1.1.2
		ingressSwitchAttenuation OBJECT-TYPE
			SYNTAX INTEGER
			ACCESS read-write
			STATUS mandatory
			DESCRIPTION
				"Attenuation value of the ingress switch mode 'attenuator'. Unit 0.01 dB."
			::= { ingressSwitchEntry 2 }

		
		-- 1.3.6.1.4.1.3715.100.61.1.1.3
		ingressSwitchAttenuationStepSize OBJECT-TYPE
			SYNTAX INTEGER (0..10000)
			ACCESS read-only
			STATUS mandatory
			DESCRIPTION
				"Attenuator step size. Unit 0.01 dB."
			::= { ingressSwitchEntry 3 }

		
		-- 1.3.6.1.4.1.3715.100.61.1.1.4
		ingressSwitchAttenuationStep OBJECT-TYPE
			SYNTAX INTEGER
			ACCESS read-write
			STATUS mandatory
			DESCRIPTION
				"Write:
				 	Attenuator step command.
				 	Value is number of steps to be stepped. Device performs step*stepSize step in decibels.
				 	If step < 0, element steps towards minimum.
				 	If step > 0, element steps towards maximum.
				 	
				 Read: 
				 	ingressSwitchAttenuation (unit 0.01 dB) after step commands. 
				 	So there's no need to read ingressSwitchAttenuation after step command to get the current value."
			::= { ingressSwitchEntry 4 }

		
		-- 1.3.6.1.4.1.3715.100.61.1.1.5
		ingressSwitchAttenuationMinimumValue OBJECT-TYPE
			SYNTAX INTEGER
			ACCESS read-only
			STATUS mandatory
			DESCRIPTION
				"Minimum value of inress switch 'attenuator'. Unit 0.01 dB."
			::= { ingressSwitchEntry 5 }

		
		-- 1.3.6.1.4.1.3715.100.61.1.1.6
		ingressSwitchAttenuationMaximumValue OBJECT-TYPE
			SYNTAX INTEGER
			ACCESS read-only
			STATUS mandatory
			DESCRIPTION
				"Maximum value of inress switch 'attenuator'. Unit 0.01 dB."
			::= { ingressSwitchEntry 6 }

		
		-- 1.3.6.1.4.1.3715.100.61.1.1.7
		ingressSwitchControlMode OBJECT-TYPE
			SYNTAX INTEGER
				{
				ingressSwitchControlModeAlarmAttenuate(1),
				ingressSwitchControlModeManual(2),
				ingressSwitchControlModeAlarmOff(3),
				ingressSwitchControlModeWarningAttenuateAlarmOff(4)
				}
			ACCESS read-write
			STATUS mandatory
			DESCRIPTION
				"Ingress switch control mode.
				1: Ingress switch (ICS) is automatically switched to attenuation/padding (typically -6 dB) when ingress alarm is active.
				2: Ingress switch controlled manually.
				3: Ingress switch (ICS) is automatically switched to off (typically -50 dB) when ingress alarm is active.
				4: Ingress switch (ICS) is automatically switched to attenuation/padding (typically -6 dB) when ingress warning is active and 
				   Ingress switch (ICS) is automatically switched to off (typically -50 dB) when ingress alarm is active.
				
				
				See also ingressSwitchControlModeVersion for supported modes."
			::= { ingressSwitchEntry 7 }

		
		-- 1.3.6.1.4.1.3715.100.61.1.1.8
		ingressSwitchActivationDelay OBJECT-TYPE
			SYNTAX INTEGER (0..65535)
			ACCESS read-write
			STATUS mandatory
			DESCRIPTION
				"Activation delay of the automatic ingress attenuation function.
				Unit 1 second."
			::= { ingressSwitchEntry 8 }

		
		-- 1.3.6.1.4.1.3715.100.61.1.1.9
		ingressSwitchDeActivationDelay OBJECT-TYPE
			SYNTAX INTEGER (0..65535)
			ACCESS read-write
			STATUS mandatory
			DESCRIPTION
				"Deactivation delay of the automatic ingress attenuation function.
				Unit 1 second."
			::= { ingressSwitchEntry 9 }

		
		-- 1.3.6.1.4.1.3715.100.61.1.1.10
		ingressSwitchControlModeVersion OBJECT-TYPE
			SYNTAX INTEGER
				{
				ingressSwitchControlModeVersion2(2),
				ingressSwitchControlModeVersion4(4)
				}
			ACCESS read-only
			STATUS mandatory
			DESCRIPTION
				"Number of modes supported by ingressSwitchControlMode.
				- If this OID is unavailable, legacy mode is supported: 1 and 2.
				- 2: Legacy mode is supported: 1 and 2.
				- 4: New modes (3 and 4) are supported in addition to legacy modes 1 and 2.
				
				Mode enumerations
				- ingressSwitchControlModeAlarmAttenuate(1),
				- ingressSwitchControlModeManual(2),
				- ingressSwitchControlModeAlarmOff(3),
				- ingressSwitchControlModeWarningAttenuateAlarmOff(4)
				"
			::= { ingressSwitchEntry 10 }

		
	
	END

--
-- TELESTE-FUNCTIONAL-INGRESS-SWITCH-MIB.mib
--
