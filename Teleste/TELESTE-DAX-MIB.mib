--
-- TELESTE-DAX-MIB.mib
-- MIB generated by MG-SOFT Visual MIB Builder 2023 (64-bit) Version 16.00  Build 1600
-- Wednesday, November 22, 2023 at 15:28:55
--

-- ****************************************************************************
-- Copyright (c) 2014 by:
-- 
-- Teleste Corporation
-- Telestenkatu 1
-- FI-20660 Littoinen, Finland
-- tel. +358 2 2605 611
-- url: http://www.teleste.com
-- 
-- Description: DAx product definitions. Note! This MIB only contains sysOID 
-- definitions for DAx. All active objects are defined in relevant
-- Teleste MIBs.
-- 
-- Revision History:
-- -----------------
-- 15, 22.11.2023, Sami Kuusisto
-- - Added dan3(00)SlopeMin and dan3(00)OutputLevelMax.
-- 
-- 14, 19.4.2023, Sami Kuusisto
-- - Added DAN300 2nd gen sysOID (dan300-2ndgen).
-- 
-- 13, 31.8.2022, Sami Kuusisto
-- - Removed das212 and das224. 
-- - Renamed dasDs0/1OutputLevel to dasDs0/1OutputTcp.
-- - Changed DAS  installation position left -> A, right -> B.
-- 
-- 12, 9.5.2022, Sami Kuusisto
-- - Added dasPsu5V75, dasRfOutputControl, dasDs0/1OutputLevel and dasInstallationPosition.
-- 
-- 11, 22.4.2022, Sami Kuusisto
-- - Added sysOID for das212 and das224.
-- 
-- 10, 30.10.2020, Sami Kuusisto
-- - Added dan3outputModuleType for DAN3.
-- 
-- 9, 15.4.2020, Sami Kuusisto
-- - Added sysOID for DAN3.
-- 
-- 8, 17.9.2019, Sami Kuusisto
-- - Added rfOperationMode and  for DAN300 1x2.
-- 
-- 7, 18.6.2019, Sami Kuusisto
-- - Added sysOID for DAN300 1x2.
-- 
-- 6, 13.4.2018, Sami Kuusisto
-- - Added psu34V to DAN300.
-- 
-- 5, 7.2.2018, Sami Kuusisto
-- - Added psu5V75 to DAN300.
-- 
-- 4, 31.1.2018, Sami Kuusisto
-- - Added bcLpf and returnPathGain to DAN300.
-- 
-- 3, 7.11.2017, Sami Kuusisto
-- - Added DAN300 sysOID.
-- 
-- 2, 13.6.2016 Sami Kuusisto
-- - Added rpdStatus, rfOutput, returnPathFilter1&2, returnPathTestPointSelection to DAN200.
-- 
-- 1, 17.11.2014 Matti Susi
-- - initial version
-- 
-- ****************************************************************************

	TELESTE-DAX-MIB DEFINITIONS ::= BEGIN
 
		IMPORTS
			OBJECT-TYPE			
				FROM RFC-1212			
			dax			
				FROM TELESTE-ROOT-MIB;
	
	
	
--
-- Node definitions
--
	
-- Root object identifier for DAH products
		-- 1.3.6.1.4.1.3715.12.100
		dah OBJECT IDENTIFIER ::= { dax 100 }

		
-- Object identifier for DAH100
		-- 1.3.6.1.4.1.3715.12.100.100
		dah100 OBJECT IDENTIFIER ::= { dah 100 }

		
-- Object identifier for DAH200
		-- 1.3.6.1.4.1.3715.12.100.200
		dah200 OBJECT IDENTIFIER ::= { dah 200 }

		
-- Root object identifier for DAn products
		-- 1.3.6.1.4.1.3715.12.200
		dan OBJECT IDENTIFIER ::= { dax 200 }

		
		-- 1.3.6.1.4.1.3715.12.200.3
		dan3 OBJECT IDENTIFIER ::= { dan 3 }

		
		-- 1.3.6.1.4.1.3715.12.200.3.1
		dan3-generations OBJECT IDENTIFIER ::= { dan3 1 }

		
		-- 1.3.6.1.4.1.3715.12.200.3.1.1
		dan3-1stgen OBJECT-TYPE
			SYNTAX INTEGER
			ACCESS read-write
			STATUS mandatory
			DESCRIPTION
				"sysOID for 1st generation of DAN3 mini RPD node."
			::= { dan3-generations 1 }

		
		-- 1.3.6.1.4.1.3715.12.200.3.2
		dan3outputModuleType OBJECT-TYPE
			SYNTAX INTEGER
				{
				outputModuleShort(1),
				outputModuleAC6124v1(2),
				outputModuleAC6124v2(3),
				outputModuleAC6113(4),
				outputModuleAC6114(5),
				outputModuleAC6115(6),
				outputModuleAC6117(7),
				outputModuleAC6120(12),
				outputModuleOpen(13),
				outputModuleReserved(14),
				outputModuleUnknown(15),
				outputModuleNA(16)
				}
			ACCESS read-only
			STATUS mandatory
			DESCRIPTION
				"Output output module type.
				1: short
				2: AC6124v1 (unknown module)
				3: AC6124v2
				4: AC6113
				5: AC6114
				6: AC6115
				7: AC6117
				12: AC6120
				13: open
				14: reserved
				15: unknown
				16: N/A"
			::= { dan3 2 }

		
		-- 1.3.6.1.4.1.3715.12.200.3.3
		dan3SlopeMin OBJECT-TYPE
			SYNTAX INTEGER
			ACCESS read-only
			STATUS mandatory
			DESCRIPTION
				"Slope minimum value.
				Unit 0.01 dB."
			::= { dan3 3 }

		
		-- 1.3.6.1.4.1.3715.12.200.3.4
		dan3OutputLevelMax OBJECT-TYPE
			SYNTAX INTEGER
			ACCESS read-only
			STATUS mandatory
			DESCRIPTION
				"OutputLevelMaximum value.
				Unit 0.01 dBµV."
			::= { dan3 4 }

		
-- Object identifier for DAN200
		-- 1.3.6.1.4.1.3715.12.200.200
		dan200 OBJECT IDENTIFIER ::= { dan 200 }

		
		-- 1.3.6.1.4.1.3715.12.200.200.1
		rpdStatus OBJECT-TYPE
			SYNTAX INTEGER
			ACCESS read-only
			STATUS mandatory
			DESCRIPTION
				"RPD status bits. ok/fail: '1'/'0': TBD
				Bit 0: Power 0: ok/fail
				Bit 1: Power 1: ok/fail
				Bit 2: 3.3 VV out meas: ok/fail
				Bit 3: Node FRX Ctrl
				Bit 4: Led status
				Bit 5: Led Alarm
				Bit 6: N/A
				Bit 7: EXT_nRST_CASA
				
				Bit 8: Downstream 0 config: ok/fail
				Bit 9: Downstream 1 config: ok/fail
				Bit 10: Upstream 0 config: ok/fail
				Bit 11: Upstream 1 config: ok/fail
				Bit 12: Receiver 0: ok/fail
				Bit 13: Receiver 1: ok/fail
				Bit 14: RF 0: ok/fail
				Bit 15: RF 1: ok/fail"
			::= { dan200 1 }

		
		-- 1.3.6.1.4.1.3715.12.200.200.2
		rfOutput OBJECT-TYPE
			SYNTAX INTEGER
			ACCESS read-only
			STATUS mandatory
			DESCRIPTION
				"RF output. Unit 0,01 dBm."
			::= { dan200 2 }

		
		-- 1.3.6.1.4.1.3715.12.200.200.3
		returnPathFilter1 OBJECT-TYPE
			SYNTAX INTEGER
			ACCESS read-only
			STATUS mandatory
			DESCRIPTION
				"Return path 1 filter type. 
				1: short, 
				2: CXF065, 
				4: CXF085, 
				6: CXF204, 
				12: open, 
				13: reserved, 
				14: unknown,
				15: N/A
				"
			::= { dan200 3 }

		
		-- 1.3.6.1.4.1.3715.12.200.200.4
		returnPathFilter2 OBJECT-TYPE
			SYNTAX INTEGER
			ACCESS read-only
			STATUS mandatory
			DESCRIPTION
				"Return path 2 filter type. 
				1: short, 
				2: CXF065, 
				4: CXF085, 
				6: CXF204, 
				12: open, 
				13: reserved, 
				14: unknown,
				15: N/A"
			::= { dan200 4 }

		
		-- 1.3.6.1.4.1.3715.12.200.200.5
		returnPathTestPointSelection OBJECT-TYPE
			SYNTAX INTEGER
				{
				returnPathTestPointAutomatic(1),
				returnPathTestPointReturnPath1(2),
				returnPathTestPointReturnPath2(3)
				}
			ACCESS read-write
			STATUS mandatory
			DESCRIPTION
				"Return path test point control/selection.
				1: Automatic
				2: Return path 1
				3: Return path 2"
			::= { dan200 5 }

		
		-- 1.3.6.1.4.1.3715.12.200.300
		dan300 OBJECT IDENTIFIER ::= { dan 300 }

		
		-- 1.3.6.1.4.1.3715.12.200.300.1
		bcLpf OBJECT-TYPE
			SYNTAX INTEGER
				{
				bcLpfN/A(1),
				bcLpfOther(2),
				bcLpf470MHz(3),
				bcLpf870MHz(4)
				}
			ACCESS read-write
			STATUS mandatory
			DESCRIPTION
				"BroadCast input, optical input low pass filter selection.
				1: Low pass filter not available (read only).
				2: Low pass filter other.
				3: 470 MHz low pass filter.
				4: 870 MHz low pass filter."
			::= { dan300 1 }

		
		-- 1.3.6.1.4.1.3715.12.200.300.2
		returnPathGain OBJECT-TYPE
			SYNTAX INTEGER
				{
				returnPathGainNA(1),
				returnPathGainOther(2),
				returnPathGain0dB(3),
				returnPathGain10dB(4)
				}
			ACCESS read-write
			STATUS mandatory
			DESCRIPTION
				"Return path gain selection.
				1: Return path gain not selectable (read only).
				2: Return path gain other.
				3: Return path gain 0 dB.
				4: Return path gain 10 dB."
			::= { dan300 2 }

		
		-- 1.3.6.1.4.1.3715.12.200.300.3
		psu5V75 OBJECT-TYPE
			SYNTAX INTEGER
			ACCESS read-write
			STATUS mandatory
			DESCRIPTION
				"+5.75 VDC voltage from power supply. Unit 0.01 V.
				 This object has an entry in the propertyTable."
			::= { dan300 3 }

		
		-- 1.3.6.1.4.1.3715.12.200.300.4
		psu34V OBJECT-TYPE
			SYNTAX INTEGER
			ACCESS read-write
			STATUS mandatory
			DESCRIPTION
				"+34 VDC voltage from power supply. Unit 0.01 V.
				 This object has an entry in the propertyTable."
			::= { dan300 4 }

		
		-- 1.3.6.1.4.1.3715.12.200.300.5
		rfOperationMode OBJECT-TYPE
			SYNTAX INTEGER
				{
				rfOperationMode1RfPort1x1(111),
				rfOperationMode2RfPorts1x1(112),
				rfOperationMode2RfPorts1x2(122)
				}
			ACCESS read-write
			STATUS mandatory
			DESCRIPTION
				"RF operation mode
				- 111: 1 RF port:  1x1 (1 DS, 1 US)
				- 112: 2 RF ports: 1x1 (1 DS, 1 US)
				- 122: 2 RF ports: 1x2 (1 DS, 2 US)"
			::= { dan300 5 }

		
		-- 1.3.6.1.4.1.3715.12.200.300.6
		usTestpointSelection OBJECT-TYPE
			SYNTAX INTEGER
				{
				usTestpointSelectionAutomatic(1),
				usTestpointSelectionManualUS1(2),
				usTestpointSelectionManualUS2(3)
				}
			ACCESS read-write
			STATUS mandatory
			DESCRIPTION
				"US test point selection: 
				1: automatic, 
				2: manual US1, 
				3: manual US2"
			::= { dan300 6 }

		
		-- 1.3.6.1.4.1.3715.12.200.300.7
		dan300SlopeMin OBJECT-TYPE
			SYNTAX INTEGER
			ACCESS read-only
			STATUS mandatory
			DESCRIPTION
				"Slope minimum value.
				Unit 0.01 dB."
			::= { dan300 7 }

		
		-- 1.3.6.1.4.1.3715.12.200.300.8
		dan300OutputLevelMax OBJECT-TYPE
			SYNTAX INTEGER
			ACCESS read-only
			STATUS mandatory
			DESCRIPTION
				"OutputLevelMaximum value.
				Unit 0.01 dBµV."
			::= { dan300 8 }

		
		-- 1.3.6.1.4.1.3715.12.200.300.300
		generations OBJECT IDENTIFIER ::= { dan300 300 }

		
		-- 1.3.6.1.4.1.3715.12.200.300.300.2
		dan300-2ndgen OBJECT-TYPE
			SYNTAX INTEGER
			ACCESS read-write
			STATUS mandatory
			DESCRIPTION
				"sysOID for DAN300 2nd gen RPD node."
			::= { generations 2 }

		
		-- 1.3.6.1.4.1.3715.12.200.300.300.11
		dan300-1x1 OBJECT-TYPE
			SYNTAX INTEGER
			ACCESS read-only
			STATUS mandatory
			DESCRIPTION
				"sysOID for DAN300 1x1 RPD node (same as dan300).
				This is DAN300 1st gen."
			::= { generations 11 }

		
		-- 1.3.6.1.4.1.3715.12.200.300.300.12
		dan300-1x2 OBJECT-TYPE
			SYNTAX INTEGER
			ACCESS read-only
			STATUS mandatory
			DESCRIPTION
				"sysOID for DAN300 1x2 RPD node.
				This is DAN300 1st gen."
			::= { generations 12 }

		
		-- 1.3.6.1.4.1.3715.12.300
		das OBJECT IDENTIFIER ::= { dax 300 }

		
		-- 1.3.6.1.4.1.3715.12.300.1
		dasPsu5V75 OBJECT-TYPE
			SYNTAX INTEGER
			ACCESS read-only
			STATUS mandatory
			DESCRIPTION
				"+5.75 VDC voltage from power supply. Unit 0.01 V.
				 This object has an entry in the propertyTable."
			::= { das 1 }

		
		-- 1.3.6.1.4.1.3715.12.300.2
		dasInstallationPosition OBJECT-TYPE
			SYNTAX INTEGER
				{
				dasInstallationPositionNA(1),
				dasInstallationPositionUnknown(2),
				dasInstallationPositionA(3),
				dasInstallationPositionB(4)
				}
			ACCESS read-only
			STATUS mandatory
			DESCRIPTION
				"RF module installation position in DAS2xx rack unit
				1: N/A
				2: Unknown
				3: A (left)
				4: B (right)
				"
			::= { das 2 }

		
		-- 1.3.6.1.4.1.3715.12.300.3
		dasRfOutputControl OBJECT-TYPE
			SYNTAX INTEGER
				{
				dasRfOutputDs0DisabledDs1Disabled(0),
				dasRfOutputDs0EnabledDs1Disabled(1),
				dasRfOutputDs0DisabledDs1Enabled(2),
				dasRfOutputDs0EnabledDs1Enabled(3)
				}
			ACCESS read-write
			STATUS mandatory
			DESCRIPTION
				"RF module RF output control
				0: DS0 disabled, DS1 disabled
				1: DS0 enabled,  DS1 disabled
				2: DS0 disabled, DS1 enabled 
				3: DS0 enabled,  DS1 disabled"
			::= { das 3 }

		
		-- 1.3.6.1.4.1.3715.12.300.4
		dasDs0OutputTCP OBJECT-TYPE
			SYNTAX INTEGER
			ACCESS read-only
			STATUS mandatory
			DESCRIPTION
				"RF output 1 (DS0) TCP. 0.01 dBµV."
			::= { das 4 }

		
		-- 1.3.6.1.4.1.3715.12.300.5
		dasDs1OutputTCP OBJECT-TYPE
			SYNTAX INTEGER
			ACCESS read-only
			STATUS mandatory
			DESCRIPTION
				"RF output 2 (DS1) TCP. 0.01 dBµV."
			::= { das 5 }

		
-- Generation info for DAS.
		-- 1.3.6.1.4.1.3715.12.300.99
		das-generations OBJECT IDENTIFIER ::= { das 99 }

		
		-- 1.3.6.1.4.1.3715.12.300.99.1
		das-1stgen OBJECT-TYPE
			SYNTAX INTEGER
			ACCESS read-write
			STATUS mandatory
			DESCRIPTION
				"1st generation info/sysOID for DAS.
				1st generation devices may not support this and uses 1.3.6.1.4.1.3715.12.300 as sysOID."
			::= { das-generations 1 }

		
		-- 1.3.6.1.4.1.3715.12.300.99.2
		das-2ndgen OBJECT-TYPE
			SYNTAX INTEGER
			ACCESS read-write
			STATUS mandatory
			DESCRIPTION
				"2nd generation info/sysOID for DAS."
			::= { das-generations 2 }

		
	
	END

--
-- TELESTE-DAX-MIB.mib
--
