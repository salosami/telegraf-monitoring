--
-- TELESTE-ACE-MIB.mib
-- MIB generated by MG-SOFT Visual MIB Builder 2016 (64-bit) Version 10.0  Build 1010
-- Tuesday, November 07, 2017 at 15:23:15
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-ACE-MIB
-- 
-- Description:   MIB module describing Teleste ACE series specific objects
-- 
-- Revision history:
-- -----------------
-- 5, 7.11.2017, Sami Kuusisto
-- - Added ACE8 2nd gen sysOID.
-- 
-- 4, 3.5.2016, Sami Kuusisto
-- - ACE3: Added returnPathInputOffset
-- - Added ace2.
-- 
-- 3, 1.10.2015, Sami Kuusisto
-- - Added ACE3: preSlope1GHz.
-- 
-- 2, 19.1.2015, Sami Kuusisto
-- - Added ACE3.
-- 
-- 1, 13.3.2014, Sami Kuusisto
-- - Initial version.
-- 
-- 
-- ****************************************************************************
-- 

	TELESTE-ACE-MIB DEFINITIONS ::= BEGIN
 
		IMPORTS
			OBJECT-TYPE			
				FROM RFC-1212			
			acx			
				FROM TELESTE-ROOT-MIB;
	
	
	
--
-- Node definitions
--
	
-- Teleste ACE series.
		-- 1.3.6.1.4.1.3715.11.579
		ace OBJECT IDENTIFIER ::= { acx 579 }

		
		-- 1.3.6.1.4.1.3715.11.579.2
		ace2 OBJECT IDENTIFIER ::= { ace 2 }

		
-- Teleste ACE series - ACE3 amplifier.
		-- 1.3.6.1.4.1.3715.11.579.3
		ace3 OBJECT IDENTIFIER ::= { ace 3 }

		
		-- 1.3.6.1.4.1.3715.11.579.3.1
		preSlope1GHz OBJECT-TYPE
			SYNTAX INTEGER
				{
				preSlopeFlat(1),
				preSloped(2)
				}
			ACCESS read-write
			STATUS mandatory
			DESCRIPTION
				"Forward path fixed 1.0 GHz preslope.
				
				Enumeration
				2: Enable 1.0 GHz preslope.
				1: Disable 1.0 GHz preslope."
			::= { ace3 1 }

		
		-- 1.3.6.1.4.1.3715.11.579.3.2
		returnPathInputOffset OBJECT-TYPE
			SYNTAX INTEGER
			ACCESS read-write
			STATUS mandatory
			DESCRIPTION
				"Return path input offset [-10...0 dB]. Unit 0.01 dB."
			::= { ace3 2 }

		
-- Teleste ACE series - ACE8 node.
		-- 1.3.6.1.4.1.3715.11.579.8
		ace8 OBJECT IDENTIFIER ::= { ace 8 }

		
		-- 1.3.6.1.4.1.3715.11.579.8.1
		preSlope862MHz OBJECT-TYPE
			SYNTAX INTEGER
				{
				preSlopeFlat(1),
				preSlope8dB(800)
				}
			ACCESS read-write
			STATUS mandatory
			DESCRIPTION
				"Forward path 862 MHz preslope.
				
				Enumeration
				800: 8.0 dB preslope.
				other: 0.0 dB preslope."
			::= { ace8 1 }

		
		-- 1.3.6.1.4.1.3715.11.579.8.2
		output2Enable OBJECT-TYPE
			SYNTAX INTEGER
				{
				output2Enabled(1),
				output2disabled(2)
				}
			ACCESS read-write
			STATUS mandatory
			DESCRIPTION
				"Output 2 enable/disable.
				
				1: Output 2 enabled.
				2: Output 2 disabled."
			::= { ace8 2 }

		
-- Teleste ACE series - ACE8 node generations.
		-- 1.3.6.1.4.1.3715.11.579.8.8
		ace8-generations OBJECT IDENTIFIER ::= { ace8 8 }

		
-- Teleste ACE series - ACE8 1st generation node.
		-- 1.3.6.1.4.1.3715.11.579.8.8.1
		ace8-1stgen OBJECT IDENTIFIER ::= { ace8-generations 1 }

		
-- Teleste ACE series - ACE8 2nd generation node.
		-- 1.3.6.1.4.1.3715.11.579.8.8.2
		ace8-2ndgen OBJECT IDENTIFIER ::= { ace8-generations 2 }

		
	
	END

--
-- TELESTE-ACE-MIB.mib
--
