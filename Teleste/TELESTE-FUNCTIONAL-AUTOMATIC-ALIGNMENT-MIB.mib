--
-- TELESTE-FUNCTIONAL-AUTOMATIC-ALIGNMENT-MIB.mib
-- MIB generated by MG-SOFT Visual MIB Builder 2023 (64-bit) Version 16.00  Build 1600
-- Thursday, September 21, 2023 at 13:20:52
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-AUTOMATIC-ALIGNMENT-MIB
-- 
-- Description:   MIB module describing Teleste functional automatic alignment specific objects
-- 
-- Revision history:
-- -----------------
-- 13, 21.9.2023, Sami Kuusisto
-- - Added new enums 25...28 to automaticAlignmentOptionStatus and automaticAlignmentLastRunStatus.
-- 
-- 12, 20.3.2017, Sami Kuusisto
-- - Fixed automaticAlignmentOptionStatus to read-only.
-- 
-- 11, 15.2.2017, Sami Halen
-- - Removed references to cable simulator value in texts.
-- 
-- 10, 20.12.2016, Sami Kuusisto
-- - Added states 23 and 24 to automaticAlignmentLastRunStatus and automaticAlignmentOptionStatus.
-- 
-- 9, 16.12.2016, Sami Kuusisto
-- - Added states 21 and 22 to automaticAlignmentLastRunStatus and automaticAlignmentOptionStatus.
-- 
-- 8, 23.11.2015, Sami Kuusisto
-- - Added transponderSetButtonOptionStatusUnknownModule(20) and transponderSetButtonLastRunStatusUnknownModule(20)
-- 
-- 7, 6.11.2014, Sami Kuusisto
-- - Added automaticAlignmentRunNowSelected.
-- 
-- 6, 2.4.2014, Sami Kuusisto
-- - Updated automaticAlignmentOptionValue description.
-- 
-- 5, 2.4.2014, Sami Kuusito
-- - fixed automaticAlignmentLastRunErrorIndex to RO.
-- 
-- 4, 26.3.2014, Sami Kuusisto
-- 
-- - Renamed MIB to TELESTE-FUNCTIONAL-AUTOMATIC-ALIGNMENT-MIB
-- 
-- 3, 14.3.2014, Sami Kuusisto
-- - transponderSetButtonLastRunErrorIndex
-- 
-- 2, 13.3.2014, Sami Kuusisto
-- - added transponderSetButtonOptionStatus.
-- 
-- 1, 12.3.2014, Sami Kuusisto
-- - Initial version.
-- 
-- ****************************************************************************
-- 

	TELESTE-FUNCTIONAL-AUTOMATIC-ALIGNMENT-MIB DEFINITIONS ::= BEGIN
 
		IMPORTS
			OBJECT-TYPE			
				FROM RFC-1212			
			functional			
				FROM TELESTE-ROOT-MIB;
	
	
	
--
-- Node definitions
--
	
		-- 1.3.6.1.4.1.3715.100.94
		automaticAlignment OBJECT IDENTIFIER ::= { functional 94 }

		
		-- 1.3.6.1.4.1.3715.100.94.1
		automaticAlignmentRunNow OBJECT-TYPE
			SYNTAX INTEGER
				{
				transponderSetButtonRunNow(1),
				transponderSetButtonRead(2)
				}
			ACCESS read-write
			STATUS mandatory
			DESCRIPTION
				"Run all options defined in automaticAlignmentOptions.
				1: Run now
				2: Returned when reading because SNMP v1 doesn't support write only parameters."
			::= { automaticAlignment 1 }

		
		-- 1.3.6.1.4.1.3715.100.94.2
		automaticAlignmentLastRunStatus OBJECT-TYPE
			SYNTAX INTEGER
				{
				transponderSetButtonLastRunStatusNeverRun(1),
				transponderSetButtonLastRunStatusRunning(2),
				transponderSetButtonLastRunStatusSuccess(3),
				transponderSetButtonLastRunStatusNoTunerModule(4),
				transponderSetButtonLastRunStatusWaitingForRun(16),
				transponderSetButtonLastRunStatusCanceled(17),
				transponderSetButtonLastRunStatusWarning(18),
				transponderSetButtonLastRunStatusError(19),
				transponderSetButtonLastRunStatusUnknownModule(20),
				transponderSetButtonLastRunStatusErrorSlopeBelowLowLimit(21),
				transponderSetButtonLastRunStatusErrorSlopeAboveHighLimit(22),
				transponderSetButtonLastRunStatusWarningSlopeNearLowLimit(23),
				transponderSetButtonLastRunStatusWarningSlopeNearHighLimit(24),
				transponderSetButtonLastRunStatusErrorGainBelowLowLimit(25),
				transponderSetButtonLastRunStatusErrorGainAboveHighLimit(26),
				transponderSetButtonLastRunStatusWarningGainNearLowLimit(27),
				transponderSetButtonLastRunStatusWarningGainNearHighLimit(28)
				}
			ACCESS read-only
			STATUS mandatory
			DESCRIPTION
				"Same status codes than pilotBasedAlignmentStatus.
				1 = never run
				2 = running
				3 = success
				4 = no tuner module
				5 = targets out of range
				6 = interstage slope target ouf of range
				7 = pilots not found
				8 = input slope out of range
				9 = gain target out of range
				10 = a cable simulator may be needed into the universal plug-in slot
				11 = gain or slope is saturated
				12 = unknown forward path plug-in module
				13 = alignGain2TargetOutOfRange / auxGainOutOfRange
				14 = alignInterStage2SlopeOutOfRange
				15 = alignOpticalInputPowerOutOfRange
				16 = alignWaitingForRun
				17 = alignCanceled
				18 = warning: see automaticAlignmentLastRunErrorIndex to figure out entry of automaticAlignmentOptionsTable to see the last warning.
				19 = error: see automaticAlignmentLastRunErrorIndex to figure out entry of automaticAlignmentOptionsTable to see the first error.
				20 = unknown module
				21 = error: slope below low limit / slope too low
				22 = error: slope above high limit / slope too high
				23 = warning: slope near low limit / slope too low
				24 = warning: slope near high limit / slope too high
				25 = error: gain below low limit
				26 = error: gain above high limit
				27 = warning: gain near low limit
				28 = warning: gain near high limit
				
				Status is set to 1, when device boots up."
			::= { automaticAlignment 2 }

		
		-- 1.3.6.1.4.1.3715.100.94.3
		automaticAlignmentLastRunErrorIndex OBJECT-TYPE
			SYNTAX INTEGER (0..65535)
			ACCESS read-only
			STATUS mandatory
			DESCRIPTION
				"Index of last error.
				
				- 0: if not run (at all) or no error in last run
				- index to automaticAlignmentOptionsTable, if warning or error occured during last run.
				  index is the first error index or last warning index."
			::= { automaticAlignment 3 }

		
		-- 1.3.6.1.4.1.3715.100.94.4
		automaticAlignmentOptionsTable OBJECT-TYPE
			SYNTAX SEQUENCE OF AutomaticAlignmentOptionsEntry
			ACCESS not-accessible
			STATUS mandatory
			::= { automaticAlignment 4 }

		
		-- 1.3.6.1.4.1.3715.100.94.4.1
		automaticAlignmentOptionsEntry OBJECT-TYPE
			SYNTAX AutomaticAlignmentOptionsEntry
			ACCESS not-accessible
			STATUS mandatory
			DESCRIPTION
				"A table of automatic alignment options."
			INDEX { automaticAlignmentOptionIndex }
			::= { automaticAlignmentOptionsTable 1 }

		
		AutomaticAlignmentOptionsEntry ::=
			SEQUENCE { 
				automaticAlignmentOptionIndex
					INTEGER,
				automaticAlignmentOptionName
					OCTET STRING,
				automaticAlignmentOptionEnable
					INTEGER,
				automaticAlignmentOptionValue
					INTEGER,
				automaticAlignmentOptionStatus
					INTEGER,
				automaticAlignmentOptionValue2
					INTEGER
			 }

		-- 1.3.6.1.4.1.3715.100.94.4.1.1
		automaticAlignmentOptionIndex OBJECT-TYPE
			SYNTAX INTEGER (1..65535)
			ACCESS read-write
			STATUS mandatory
			DESCRIPTION
				"Option index."
			::= { automaticAlignmentOptionsEntry 1 }

		
		-- 1.3.6.1.4.1.3715.100.94.4.1.2
		automaticAlignmentOptionName OBJECT-TYPE
			SYNTAX OCTET STRING
			ACCESS read-only
			STATUS mandatory
			DESCRIPTION
				"Human readable name of option."
			::= { automaticAlignmentOptionsEntry 2 }

		
		-- 1.3.6.1.4.1.3715.100.94.4.1.3
		automaticAlignmentOptionEnable OBJECT-TYPE
			SYNTAX INTEGER
				{
				transponderSetButtonOptionEnabled(1),
				transponderSetButtonOptionDisabled(2)
				}
			ACCESS read-write
			STATUS mandatory
			DESCRIPTION
				"Option enable/disable.
				
				1: option enabled
				2: option disabled"
			::= { automaticAlignmentOptionsEntry 3 }

		
		-- 1.3.6.1.4.1.3715.100.94.4.1.4
		automaticAlignmentOptionValue OBJECT-TYPE
			SYNTAX INTEGER
			ACCESS read-write
			STATUS mandatory
			DESCRIPTION
				"Primary value related to option. See automaticAlignmentOptionName for description of value.
				Unit (usually) 0.01, but could be also enumerated or bitfield."
			::= { automaticAlignmentOptionsEntry 4 }

		
		-- 1.3.6.1.4.1.3715.100.94.4.1.5
		automaticAlignmentOptionStatus OBJECT-TYPE
			SYNTAX INTEGER
				{
				transponderSetButtonOptionStatusNeverRun(1),
				transponderSetButtonOptionStatusRunning(2),
				transponderSetButtonOptionStatusSuccess(3),
				transponderSetButtonOptionStatusNoTunerModule(4),
				transponderSetButtonOptionStatusTargetsOutOfRange(5),
				transponderSetButtonOptionStatusInterStageSlopeTargetOutOfRange(6),
				transponderSetButtonOptionStatusPilotsNotFound(7),
				transponderSetButtonOptionStatusInputSlopeOutOfRange(8),
				transponderSetButtonOptionStatusGainTargetOutOfRange(9),
				transponderSetButtonOptionStatusCableSimulatorMayBeNeeded(10),
				transponderSetButtonOptionStatusGainOrSlopeSaturated(11),
				transponderSetButtonOptionStatusUnknownForwardPathPlug(12),
				transponderSetButtonOptionStatusGain2TargetOutOfRange(13),
				transponderSetButtonOptionStatusInterStage2SlopeOutOfRange(14),
				transponderSetButtonOptionStatusOpticalInputPowerOutOfRange(15),
				transponderSetButtonOptionStatusWaitingForRun(16),
				transponderSetButtonOptionStatusCanceled(17),
				transponderSetButtonOptionStatusUnknownModule(20),
				transponderSetButtonOptionStatusErrorSlopeBelowLowLimit(21),
				transponderSetButtonOptionStatusErrorSlopeAboveHighLimit(22),
				transponderSetButtonOptionStatusWarningSlopeNearLowLimit(23),
				transponderSetButtonOptionStatusWarningSlopeNearHighLimit(24),
				transponderSetButtonOptionStatusErrorGainBelowLowLimit(25),
				transponderSetButtonOptionStatusErrorGainAboveHighLimit(26),
				transponderSetButtonOptionStatusWarningGainNearLowLimit(27),
				transponderSetButtonOptionStatusWarningGainNearHighLimit(28)
				}
			ACCESS read-only
			STATUS mandatory
			DESCRIPTION
				"Same status codes than pilotBasedAlignmentStatus.
				1 = never run
				2 = running
				3 = success
				4 = no tuner module
				5 = targets out of range
				6 = interstage slope target ouf of range
				7 = pilots not found
				8 = input slope out of range
				9 = gain target out of range
				10 = a cable simulator may be needed into the universal plug-in slot
				11 = gain or slope is saturated
				12 = unknown forward path plug-in module
				13 = alignGain2TargetOutOfRange / auxGainOutOfRange
				14 = alignInterStage2SlopeOutOfRange
				15 = alignOpticalInputPowerOutOfRange
				16 = alignWaitingForRun
				17 = alignCanceled
				20 = unknownModule
				21 = error: slope below low limit / slope too low
				22 = error: slope above high limit / slope too high
				23 = warning: slope near low limit / slope too low
				24 = warning: slope near high limit / slope too high
				25 = error: gain below low limit
				26 = error: gain above high limit
				27 = warning: gain near low limit
				28 = warning: gain near high limit
				
				All table statuses are set to 1, when device boots up.
				
				All table statuses which are not run at this time, are set to 1.
				
				All table statuses are set to 2, when one (or all) is started.
				
				If one option ends to error, then all the rest (bigger indexes) are set to 17 and 
				transponderSetButtonLastRunErrorIndex is set to this index and transponderSetButtonLastRunStatus is set to 19.
				So the first error index is visible.
				
				If one (or more) option ends to warning, then all the rest are run similar as the option ends with 3 and 
				transponderSetButtonLastRunErrorIndex is set to this index and transponderSetButtonLastRunStatus is set to 18.
				So the last warning index is visible.
				"
			::= { automaticAlignmentOptionsEntry 5 }

		
		-- 1.3.6.1.4.1.3715.100.94.4.1.6
		automaticAlignmentOptionValue2 OBJECT-TYPE
			SYNTAX INTEGER
			ACCESS read-write
			STATUS mandatory
			DESCRIPTION
				"Secondary value related to option. See automaticAlignmentOptionName for description of value.
				Unit (usually) 0.01, but could be also enumerated or bitfield."
			::= { automaticAlignmentOptionsEntry 6 }

		
		-- 1.3.6.1.4.1.3715.100.94.5
		automaticAlignmentRunNowSelected OBJECT-TYPE
			SYNTAX INTEGER
			ACCESS read-write
			STATUS mandatory
			DESCRIPTION
				"Run now selected options (bitmask; multiple bits are allowed).
				
				Index for option in automaticAlignmentOptionsTable is in format 2^(bit+1).
				E.g. automaticAlignmentOptionIndex.8 means that 8=2^3, where (bit+1) is 3, so bit = 2.
				
				Bit 0: 0x0001
				Bit 1: 0x0002
				Bit 2: 0x0004
				Bit 3: 0x0008
				Bit 4: 0x0010
				Bit 5: 0x0020
				Bit 6: 0x0040
				Bit 7: 0x0080
				Bit 8: 0x0100
				Bit 9: 0x0200
				Bit 10: 0x0400
				Bit 11: 0x0800
				etc.
				
				Note that some options may override others.
				
				Read: Options bitmask run last time. If no options run, returns 0.
				Write: Bitmask for options to be run immediately. Note! Options are not stored to non-volatile memory and selections on automaticAlignemntOptionsTable (automaticAlignmentOptionEnable) are not affected."
			::= { automaticAlignment 5 }

		
	
	END

--
-- TELESTE-FUNCTIONAL-AUTOMATIC-ALIGNMENT-MIB.mib
--
