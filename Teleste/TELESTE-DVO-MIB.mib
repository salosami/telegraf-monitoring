--
-- TELESTE-DVO-MIB.mib
-- MIB generated by MG-SOFT Visual MIB Builder Version 4.0 Build 349
-- Wednesday, January 17, 2007 at 10:50:57
--

-- **************************************************************************
-- Copyright (c) 2000-2006 by:
-- 
-- Teleste Corporation
-- Seponkatu 1
-- FIN-20660 Littoinen, Finland
-- tel. +358 2 2605 611
-- url: http://www.teleste.com
-- 
-- Description: DVO module specific objects
-- 
-- Revision History:
-- -----------------
-- 1.01, 17.1.2007, Matti Susi
-- - Added sysOID placeholders for DBM100 and DBM200
-- 
-- 1.0, 21.12.2006, Matti Susi
-- - First official release
--  
-- **************************************************************************
-- 

	TELESTE-DVO-MIB DEFINITIONS ::= BEGIN
 
		IMPORTS
			dvo			
				FROM TELESTE-ROOT-MIB;
	
	
	
--
-- Node definitions
--
	
		-- 1.3.6.1.4.1.3715.5.101
		dvo101 OBJECT IDENTIFIER ::= { dvo 101 }

		
		-- 1.3.6.1.4.1.3715.5.151
		dvo151 OBJECT IDENTIFIER ::= { dvo 151 }

		
		-- 1.3.6.1.4.1.3715.5.201
		dvo201 OBJECT IDENTIFIER ::= { dvo 201 }

		
		-- 1.3.6.1.4.1.3715.5.202
		dvo202 OBJECT IDENTIFIER ::= { dvo 202 }

		
		-- 1.3.6.1.4.1.3715.5.301
		dvo301 OBJECT IDENTIFIER ::= { dvo 301 }

		
		-- 1.3.6.1.4.1.3715.5.302
		dvo302 OBJECT IDENTIFIER ::= { dvo 302 }

		
		-- 1.3.6.1.4.1.3715.5.303
		dvo303 OBJECT IDENTIFIER ::= { dvo 303 }

		
		-- 1.3.6.1.4.1.3715.5.371
		dvo371 OBJECT IDENTIFIER ::= { dvo 371 }

		
		-- 1.3.6.1.4.1.3715.5.421
		dvo421 OBJECT IDENTIFIER ::= { dvo 421 }

		
		-- 1.3.6.1.4.1.3715.5.616
		dvo616 OBJECT IDENTIFIER ::= { dvo 616 }

		
		-- 1.3.6.1.4.1.3715.5.623
		dvo623 OBJECT IDENTIFIER ::= { dvo 623 }

		
		-- 1.3.6.1.4.1.3715.5.624
		dvo624 OBJECT IDENTIFIER ::= { dvo 624 }

		
		-- 1.3.6.1.4.1.3715.5.700
		dvo700 OBJECT IDENTIFIER ::= { dvo 700 }

		
		-- 1.3.6.1.4.1.3715.5.713
		dvo713 OBJECT IDENTIFIER ::= { dvo 713 }

		
		-- 1.3.6.1.4.1.3715.5.716
		dvo716 OBJECT IDENTIFIER ::= { dvo 716 }

		
		-- 1.3.6.1.4.1.3715.5.719
		dvo719 OBJECT IDENTIFIER ::= { dvo 719 }

		
		-- 1.3.6.1.4.1.3715.5.722
		dvo722 OBJECT IDENTIFIER ::= { dvo 722 }

		
		-- 1.3.6.1.4.1.3715.5.726
		dvo726 OBJECT IDENTIFIER ::= { dvo 726 }

		
		-- 1.3.6.1.4.1.3715.5.771
		dvo771 OBJECT IDENTIFIER ::= { dvo 771 }

		
		-- 1.3.6.1.4.1.3715.5.801
		dvo801 OBJECT IDENTIFIER ::= { dvo 801 }

		
		-- 1.3.6.1.4.1.3715.5.802
		dvo802 OBJECT IDENTIFIER ::= { dvo 802 }

		
		-- 1.3.6.1.4.1.3715.5.900
		dvo900 OBJECT IDENTIFIER ::= { dvo 900 }

		
		-- 1.3.6.1.4.1.3715.5.901
		dvo901 OBJECT IDENTIFIER ::= { dvo 901 }

		
		-- 1.3.6.1.4.1.3715.5.902
		dvo902 OBJECT IDENTIFIER ::= { dvo 902 }

		
		-- 1.3.6.1.4.1.3715.5.999
		dmm OBJECT IDENTIFIER ::= { dvo 999 }

		
-- Root for DMM200 module
		-- 1.3.6.1.4.1.3715.5.999.100
		dmm100 OBJECT IDENTIFIER ::= { dmm 100 }

		
-- Root for DMM200 module
		-- 1.3.6.1.4.1.3715.5.999.200
		dmm200 OBJECT IDENTIFIER ::= { dmm 200 }

		
-- Root for DMM200 module
		-- 1.3.6.1.4.1.3715.5.999.201
		dmm201 OBJECT IDENTIFIER ::= { dmm 201 }

		
		-- 1.3.6.1.4.1.3715.5.1000
		dbm OBJECT IDENTIFIER ::= { dvo 1000 }

		
-- Place holder for DBM100 sysOID
		-- 1.3.6.1.4.1.3715.5.1000.100
		dbm100 OBJECT IDENTIFIER ::= { dbm 100 }

		
-- Place holder for DBM200 sysOID
		-- 1.3.6.1.4.1.3715.5.1000.200
		dbm200 OBJECT IDENTIFIER ::= { dbm 200 }

		
	
	END

--
-- TELESTE-DVO-MIB.mib
--
