--
-- TELESTE-FUNCTIONAL-FUNCTIONS-MIB.mib
-- MIB generated by MG-SOFT Visual MIB Builder 2021 (64-bit) Version 15.00  Build 1510
-- Friday, October 15, 2021 at 10:25:05
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-FUNCTIONS-MIB
-- 
-- Description:   MIB module describing Teleste functional functions interface specific objects
-- 
-- Revision history:
-- -----------------
-- 3, 15.10.2021, Sami Kuusisto
-- - Added functionsStatusFunctionsFailed(21) to functionsStatus.
-- 
-- 2, 7.12.2016, Sami Kuusisto
-- - Added functionsNumberOfVariables and functionsVariableTable.
-- 
-- 1, 2.12.2016, Sami Kuusisto
-- - Initial version.
-- 
-- ****************************************************************************
-- 

	TELESTE-FUNCTIONAL-FUNCTIONS-MIB DEFINITIONS ::= BEGIN
 
		IMPORTS
			OBJECT-TYPE			
				FROM RFC-1212			
			functional			
				FROM TELESTE-ROOT-MIB;
	
	
	
--
-- Node definitions
--
	
		-- 1.3.6.1.4.1.3715.100.102
		functions OBJECT IDENTIFIER ::= { functional 102 }

		
		-- 1.3.6.1.4.1.3715.100.102.1
		functionControl OBJECT-TYPE
			SYNTAX INTEGER
				{
				functionControlEnabled(1),
				functionControlDisabled(2)
				}
			ACCESS read-write
			STATUS mandatory
			DESCRIPTION
				"Function control.
				1: Enabled
				2: Disabled"
			::= { functions 1 }

		
		-- 1.3.6.1.4.1.3715.100.102.2
		functionsStatus OBJECT-TYPE
			SYNTAX INTEGER
				{
				functionsStatusFunctionsRunning(1),
				functionsStatusFunctionsMissing(2),
				functionsStatusTooManyUnits(3),
				functionsStatusMemoryFull(4),
				functionsStatusInvalidHeader(5),
				functionsStatusInvalidConstant(6),
				functionsStatusUndefinedConstant(7),
				functionsStatusInvalidTypeFiled(8),
				functionsStatusUnknownModule(9),
				functionsStatusInvalidFlagSetting(10),
				functionsStatusInvalidTypeField(11),
				functionsStatusUnknownOperand(12),
				functionsStatusUndefinedCommand(13),
				functionsStatusUnknownMediaData(14),
				functionsStatusChecksumError(15),
				functionsStatusReserved16(16),
				functionsStatusReserved17(17),
				functionsStatusMissingProductKey(18),
				functionsStatusSerialNumberMismatch(19),
				functionsStatusFunctionsDisabled(20),
				functionsStatusFunctionsFailed(21)
				}
			ACCESS read-only
			STATUS mandatory
			DESCRIPTION
				"Status of functions.
				1: Functions running
				2: Functions missing.
				3: Too many units
				4: Memory full
				5: Invalid header
				6: Invalid constant
				7: Undefined constant
				8: Invalid type field
				9: Unknown module
				10: Invalid flag setting
				11: Invalid type field setting
				12: Unknown operand
				13: Undefined command
				14: Unknown media data
				15: Checksum error
				16: Reserved
				17: Reserved
				18: Missing product key
				19: Serial number mismatch
				20: Functions disabled
				21: Functions failed
				"
			::= { functions 2 }

		
		-- 1.3.6.1.4.1.3715.100.102.3
		functionLoopTime OBJECT-TYPE
			SYNTAX INTEGER
			ACCESS read-only
			STATUS mandatory
			DESCRIPTION
				"Function file single loop execution time in 0.01 seconds."
			::= { functions 3 }

		
		-- 1.3.6.1.4.1.3715.100.102.4
		functionNumberOfProgrammableAlarms OBJECT-TYPE
			SYNTAX INTEGER
			ACCESS read-only
			STATUS mandatory
			DESCRIPTION
				"Number of programmable alarms in functionProgrammableAlarmTable."
			::= { functions 4 }

		
		-- 1.3.6.1.4.1.3715.100.102.5
		functionProgrammableAlarmTable OBJECT-TYPE
			SYNTAX SEQUENCE OF FunctionProgrammableAlarmEntry
			ACCESS not-accessible
			STATUS mandatory
			DESCRIPTION
				"Table of programmable alarms."
			::= { functions 5 }

		
		-- 1.3.6.1.4.1.3715.100.102.5.1
		functionProgrammableAlarmEntry OBJECT-TYPE
			SYNTAX FunctionProgrammableAlarmEntry
			ACCESS not-accessible
			STATUS mandatory
			INDEX { functionProgrammableAlarmIndex }
			::= { functionProgrammableAlarmTable 1 }

		
		FunctionProgrammableAlarmEntry ::=
			SEQUENCE { 
				functionProgrammableAlarmIndex
					INTEGER,
				functionProgrammableAlarmStatus
					INTEGER
			 }

		-- 1.3.6.1.4.1.3715.100.102.5.1.1
		functionProgrammableAlarmIndex OBJECT-TYPE
			SYNTAX INTEGER (1..65535)
			ACCESS read-write
			STATUS mandatory
			DESCRIPTION
				"Index of programmable alarm.
				RW index, because SNMP v1 doesn't support not-accessible.
				"
			::= { functionProgrammableAlarmEntry 1 }

		
		-- 1.3.6.1.4.1.3715.100.102.5.1.2
		functionProgrammableAlarmStatus OBJECT-TYPE
			SYNTAX INTEGER
				{
				functionAlarmStatusNoAlarm(1),
				functionAlarmStatusAlarm(2)
				}
			ACCESS read-only
			STATUS mandatory
			DESCRIPTION
				"Current status of programmable alarm.
				1: No alarm
				2: Alarm"
			::= { functionProgrammableAlarmEntry 2 }

		
		-- 1.3.6.1.4.1.3715.100.102.6
		functionsNumberOfVariables OBJECT-TYPE
			SYNTAX INTEGER
			ACCESS read-only
			STATUS mandatory
			DESCRIPTION
				"Number of (debugging) variables.
				If (debugging) variables are not supported, functionsNumberOfVariables is 0."
			::= { functions 6 }

		
		-- 1.3.6.1.4.1.3715.100.102.7
		functionsVariableTable OBJECT-TYPE
			SYNTAX SEQUENCE OF FunctionsVariableEntry
			ACCESS not-accessible
			STATUS mandatory
			DESCRIPTION
				"Table of (debugging) variables."
			::= { functions 7 }

		
		-- 1.3.6.1.4.1.3715.100.102.7.1
		functionsVariableEntry OBJECT-TYPE
			SYNTAX FunctionsVariableEntry
			ACCESS not-accessible
			STATUS mandatory
			INDEX { functionsVariableIndex }
			::= { functionsVariableTable 1 }

		
		FunctionsVariableEntry ::=
			SEQUENCE { 
				functionsVariableIndex
					INTEGER,
				functionsVariableValue
					INTEGER
			 }

		-- 1.3.6.1.4.1.3715.100.102.7.1.1
		functionsVariableIndex OBJECT-TYPE
			SYNTAX INTEGER (1..65535)
			ACCESS read-write
			STATUS mandatory
			DESCRIPTION
				"Index of function variable.
				RW index, because SNMP v1 doesn't support not-accessible."
			::= { functionsVariableEntry 1 }

		
		-- 1.3.6.1.4.1.3715.100.102.7.1.2
		functionsVariableValue OBJECT-TYPE
			SYNTAX INTEGER
			ACCESS read-write
			STATUS mandatory
			DESCRIPTION
				"Function variable value.
				Functions overrides these values, if function file uses variable. Otherwise variable can be used to provide constants to be used in functions.
				Unit is function dependent."
			::= { functionsVariableEntry 2 }

		
	
	END

--
-- TELESTE-FUNCTIONAL-FUNCTIONS-MIB.mib
--
