--
-- TELESTE-IAC-MIB.mib
-- MIB generated by MG-SOFT Visual MIB Builder Version 4.0 Build 349
-- Thursday, August 21, 2008 at 09:54:51
--

-- ****************************************************************************
-- Copyright (c) 2008 by:
-- 
-- Teleste Corporation
-- Seponkatu 1
-- FIN-20660 Littoinen, Finland
-- tel. +358 2 2605 611
-- url: http://www.teleste.com
-- 
-- Module Name: TELESTE-IAC-MIB
-- 
-- Description: MIB module describing objects for IAC module
--              in any Teleste device
-- 
-- Revision History:
-- -----------------
-- 0.1,  21.8.2008, Matti Susi
-- - Initial version
-- 
-- ****************************************************************************
-- 
-- 

	TELESTE-IAC-MIB DEFINITIONS ::= BEGIN
 
		IMPORTS
			OBJECT-TYPE			
				FROM RFC-1212			
			TRAP-TYPE			
				FROM RFC-1215			
			enterprises, IpAddress, Gauge			
				FROM RFC1155-SMI;
	
	
--
-- Node definitions
--
	
		-- 1.3.6.1.4.1.5828
		proxilliantRoot OBJECT IDENTIFIER ::= { enterprises 5828 }

		
-- subtree for product specific objects and events
		-- 1.3.6.1.4.1.5828.3
		proxilliantProducts OBJECT IDENTIFIER ::= { proxilliantRoot 3 }

		
		-- 1.3.6.1.4.1.5828.3.2
		iacRoot OBJECT IDENTIFIER ::= { proxilliantProducts 2 }

		
-- IAC objects
		-- 1.3.6.1.4.1.5828.3.2.1
		statisticsAlert OBJECT-TYPE
			SYNTAX INTEGER
			ACCESS read-write
			STATUS mandatory
			DESCRIPTION
				"Used by the operator to start the statistics in the IAC.
				Any value starts the statistics.
				When the object is read an undefined value is returned."
			::= { iacRoot 1 }

		
		-- 1.3.6.1.4.1.5828.3.2.2
		trapIPAddress OBJECT-TYPE
			SYNTAX IpAddress
			ACCESS read-write
			STATUS mandatory
			DESCRIPTION
				"The IP address where traps should be sent."
			::= { iacRoot 2 }

		
		-- 1.3.6.1.4.1.5828.3.2.3
		iacIPAddress OBJECT-TYPE
			SYNTAX IpAddress
			ACCESS read-write
			STATUS mandatory
			DESCRIPTION
				"The IP address of the IAC."
			::= { iacRoot 3 }

		
-- IAC status objects
		-- 1.3.6.1.4.1.5828.3.2.4
		iacStatus OBJECT IDENTIFIER ::= { iacRoot 4 }

		
		-- 1.3.6.1.4.1.5828.3.2.4.1
		swVersion OBJECT-TYPE
			SYNTAX OCTET STRING
			ACCESS read-only
			STATUS mandatory
			DESCRIPTION
				"The version of the software executing in the IAC. 
				The four most significant bits are holding Release and
				the four least significant bits are holding Version"
			::= { iacStatus 1 }

		
		-- 1.3.6.1.4.1.5828.3.2.4.2
		hwVersion OBJECT-TYPE
			SYNTAX OCTET STRING
			ACCESS read-only
			STATUS mandatory
			DESCRIPTION
				"The version of the IAC hardware.
				The four most significant bits are holding Release and
				the four least significant bits are holding Version"
			::= { iacStatus 2 }

		
		-- 1.3.6.1.4.1.5828.3.2.4.3
		systemMode OBJECT-TYPE
			SYNTAX INTEGER
				{
				normal(0),
				production(1),
				capture(2),
				programming(3)
				}
			ACCESS read-only
			STATUS mandatory
			DESCRIPTION
				"The operational mode of the IAC."
			::= { iacStatus 3 }

		
		-- 1.3.6.1.4.1.5828.3.2.4.4
		statusCheck OBJECT-TYPE
			SYNTAX OCTET STRING
			ACCESS read-only
			STATUS mandatory
			DESCRIPTION
				"Indicates Status Check-failure for this IAC
				
				Bit 0  ROM Test = OK(1) or Failure(0) detected
				Bit 1  RAM1 Test = OK(1) or Failure(0) detected
				Bit 2  RAM2 Test = OK(1) or Failure(0) detected
				Bit 3  Install Test = OK(1) or Failure(0) detected
				Bit 4  Tamp = IAC is closed(1) or IAC is open(0)
				Bit 5  Initialised = Initialised(1) or Uninitialised(0)
				Bit 6  Not used, always 1
				Bit 7  Not used, always 1."
			::= { iacStatus 4 }

		
		-- 1.3.6.1.4.1.5828.3.2.4.5
		linkErrors OBJECT-TYPE
			SYNTAX Gauge
			ACCESS read-only
			STATUS mandatory
			DESCRIPTION
				"The number of linkErrors that has been detected by this IAC since last GetRequest."
			::= { iacStatus 5 }

		
		-- 1.3.6.1.4.1.5828.3.2.4.6
		seqErrors OBJECT-TYPE
			SYNTAX Gauge
			ACCESS read-only
			STATUS mandatory
			DESCRIPTION
				"The number of sequence errors that has been detected by this IAC since last GetRequest."
			::= { iacStatus 6 }

		
		-- 1.3.6.1.4.1.5828.3.2.4.7
		applErrors OBJECT-TYPE
			SYNTAX Gauge
			ACCESS read-only
			STATUS mandatory
			DESCRIPTION
				"The number of application errors detected by this IAC since last GetRequest."
			::= { iacStatus 7 }

		
		-- 1.3.6.1.4.1.5828.3.2.4.8
		otherErrors OBJECT-TYPE
			SYNTAX Gauge
			ACCESS read-only
			STATUS mandatory
			DESCRIPTION
				"The number of other errors detected by this IAC since last GetRequest."
			::= { iacStatus 8 }

		
-- IAC monitor status objects
		-- 1.3.6.1.4.1.5828.3.2.5
		iacMonitorStatus OBJECT IDENTIFIER ::= { iacRoot 5 }

		
		-- 1.3.6.1.4.1.5828.3.2.5.1
		nofLongEvents OBJECT-TYPE
			SYNTAX Gauge
			ACCESS read-only
			STATUS mandatory
			DESCRIPTION
				"The number of long events detected by the IAC during the last minute.
				
				Long events are events longer than the threshold defined by 
				'iacMib.monitorSettings.longEventDef'."
			::= { iacMonitorStatus 1 }

		
		-- 1.3.6.1.4.1.5828.3.2.5.2
		nofShortEvents OBJECT-TYPE
			SYNTAX Gauge
			ACCESS read-only
			STATUS mandatory
			DESCRIPTION
				"The number of short events detected by the IAC during 1 second. The value is
				an average over the last minute.
				
				Short events are events shorter than the threshold defined by 
				'iacMib.monitorSettings.shortEventDef'."
			::= { iacMonitorStatus 2 }

		
		-- 1.3.6.1.4.1.5828.3.2.5.3
		nofBroadEvents OBJECT-TYPE
			SYNTAX Gauge
			ACCESS read-only
			STATUS mandatory
			DESCRIPTION
				"The number of broad events detected by the IAC during 1 second. The value is
				an average over the last minute.
				
				Broad events are defined by
				'iacMib.monitorSettings.broadEventDef'."
			::= { iacMonitorStatus 3 }

		
		-- 1.3.6.1.4.1.5828.3.2.5.4
		nofUnExpEvents OBJECT-TYPE
			SYNTAX Gauge
			ACCESS read-only
			STATUS mandatory
			DESCRIPTION
				"The number of unexpected events detected by the IAC during 1 second.
				The value is an average over the last minute.
				
				Unexpected events are defined by
				'iacMib.monitorSettings.unExpEventDef'."
			::= { iacMonitorStatus 4 }

		
		-- 1.3.6.1.4.1.5828.3.2.5.5
		tampStatus OBJECT-TYPE
			SYNTAX INTEGER
				{
				nok(0),
				ok(1)
				}
			ACCESS read-only
			STATUS mandatory
			DESCRIPTION
				"Status of tampering event.
				OK = 1.
				NOK = 0
				
				The status for the tampering event.
				
				When the IAC is opened the tampEvent status is set to NOK.
				When the IAC is closed the tampEvent status is set to OK.
				
				There is no default value. The tampStatus is immediately set within the IAC.
				The monitor functions are activated by updating the monitorSettings."
			::= { iacMonitorStatus 5 }

		
		-- 1.3.6.1.4.1.5828.3.2.5.6
		longEventStatus OBJECT-TYPE
			SYNTAX INTEGER
				{
				nok(0),
				ok(1)
				}
			ACCESS read-only
			STATUS mandatory
			DESCRIPTION
				"The status for the longEvents (as defined by
				'iacMib.monitorSettings.longEventDef').
				
				If the number of long events during the last 1 minute in the IAC has exceeded
				the threshold ('iacMib.monitorSettings.nofLongEventThresh'), the value is NOK.
				If the number of long events is below the threshold, the value is OK.
				
				When the status is changed in the IAC (either from OK to NOK,
				or from NOK to OK) a longEvent is sent.
				
				The default value is OK."
			::= { iacMonitorStatus 6 }

		
		-- 1.3.6.1.4.1.5828.3.2.5.7
		shortEventStatus OBJECT-TYPE
			SYNTAX INTEGER
				{
				nok(0),
				ok(1)
				}
			ACCESS read-only
			STATUS mandatory
			DESCRIPTION
				"The status for the shortEvents (as defined by
				'iacMib.monitorSettings.shortEventDef').
				
				If the number of short events during the last 1 second in the IAC has exceeded
				the threshold ('iacMib.monitorSettings.nofShortEventThresh'), the value is NOK.
				If the number of short events is below the threshold, the value is OK.
				
				When the status is changed in the IAC (either from OK to NOK,
				or from NOK to OK) a shortEvent is sent.
				
				The default value is OK."
			::= { iacMonitorStatus 7 }

		
		-- 1.3.6.1.4.1.5828.3.2.5.8
		broadEventStatus OBJECT-TYPE
			SYNTAX INTEGER
				{
				nok(0),
				ok(1)
				}
			ACCESS read-only
			STATUS mandatory
			DESCRIPTION
				"The status for the broadEvents (as defined by
				'iacMib.monitorSettings.broadEventDef').
				
				If the number of broad events during the last 1 second in the IAC has exceeded
				the threshold ('iacMib.monitorSettings.nofBroadEventThresh'), the value is NOK.
				If the number of broad events is below the threshold, the value is OK.
				
				When the status is changed in the IAC (either from OK to NOK,
				or from NOK to OK) a broadEvent is sent.
				
				The default value is OK."
			::= { iacMonitorStatus 8 }

		
		-- 1.3.6.1.4.1.5828.3.2.5.9
		unExpEventStatus OBJECT-TYPE
			SYNTAX INTEGER
				{
				nok(0),
				ok(1)
				}
			ACCESS read-only
			STATUS mandatory
			DESCRIPTION
				"The status for the unExpEvents (as defined by
				'iacMib.monitorSettings.unExpEventDef').
				
				If the number of unExp events during the last 1 second in the IAC has exceeded
				the threshold ('iacMib.monitorSettings.nofUnExpEventThresh'), the value is NOK.
				If the number of unExp events is below the threshold, the value is OK.
				
				When the status is changed in the IAC (either from OK to NOK,
				or from NOK to OK) a unExpEvent is sent.
				
				The default value is OK."
			::= { iacMonitorStatus 9 }

		
-- IAC monitor settings
		-- 1.3.6.1.4.1.5828.3.2.6
		iacMonitorSettings OBJECT IDENTIFIER ::= { iacRoot 6 }

		
		-- 1.3.6.1.4.1.5828.3.2.6.1
		longEventDef OBJECT-TYPE
			SYNTAX Gauge
			ACCESS read-write
			STATUS mandatory
			DESCRIPTION
				"Defines the threshold value for a long upstream event for this IAC.
				
				The longEvent is given in units of ms."
			::= { iacMonitorSettings 1 }

		
		-- 1.3.6.1.4.1.5828.3.2.6.2
		shortEventDef OBJECT-TYPE
			SYNTAX Gauge
			ACCESS read-write
			STATUS mandatory
			DESCRIPTION
				"Defines the threshold value for a short upstream event for this IAC.
				
				The shortEvent is given in units of us."
			::= { iacMonitorSettings 2 }

		
		-- 1.3.6.1.4.1.5828.3.2.6.3
		broadEventDef OBJECT-TYPE
			SYNTAX OCTET STRING
			ACCESS read-write
			STATUS mandatory
			DESCRIPTION
				"Defines a broad event for this IAC.
				
				A broadEvent is defined as the combination of filterbanks it activates.
				The variable is a 4 bit representation of the four possible filterbanks
				where each bit correlates to one of the filterbanks. A broad event definition
				can then be defined as events that simultaneously has activated a combination
				of filterbanks.
				Ex: '1111' defines the broad event that has activated all filterbanks simultaneously.
				Ex: '1010' defines the broad event that has activated filterbank 1 and 3, but not 2 and 4."
			::= { iacMonitorSettings 3 }

		
		-- 1.3.6.1.4.1.5828.3.2.6.4
		unExpEventDef OBJECT-TYPE
			SYNTAX OCTET STRING
			ACCESS read-write
			STATUS mandatory
			DESCRIPTION
				"Defines an unexpected event for this IAC.
				
				An unexpected event is defined as the combination of filterbanks it activates.
				The variable is a 4 bit representation of the four possible filterbanks
				where each bit correlates to one of the filterbanks. An unexpected event definition
				can then be defined as events that simultaneously has activated a combination
				of filterbanks.
				Ex: '1111' defines the unexp event that has activated all filterbanks simultaneously.
				Ex: '1010' defines the unexp event that has activated filterbank 1 and 3, but not 2 and 4."
			::= { iacMonitorSettings 4 }

		
		-- 1.3.6.1.4.1.5828.3.2.6.5
		nofLongEventThresh OBJECT-TYPE
			SYNTAX Gauge
			ACCESS read-write
			STATUS mandatory
			DESCRIPTION
				"The number of longEvents in 1 minute required for the IAC to set
				'iacMib.monitorStatus.longEventStatus' to NOK.
				If the 'longEventStatus' in the IAC changes (either from OK to
				NOK, or from NOK to OK) it sends a monitor status message.
				
				If this MIB-variable is set to 0, this functionality is disabled. I.e within
				the IAC nofLongEvents are still stored, but 'iacMib.monitorStatus.
				longEventStatus' is not set, resulting in that no monitor status message is
				sent."
			::= { iacMonitorSettings 5 }

		
		-- 1.3.6.1.4.1.5828.3.2.6.6
		nofShortEventThresh OBJECT-TYPE
			SYNTAX Gauge
			ACCESS read-write
			STATUS mandatory
			DESCRIPTION
				"The number of shortEvents in 1 second required for the IAC to set
				'iacMib.monitorStatus.shortEventStatus' to NOK.
				If the 'shortEventStatus' in the IAC changes (either from OK to
				NOK, or from NOK to OK) it sends a monitor status message.
				
				If this MIB-variable is set to 0, this functionality is disabled. I.e within
				the IAC nofShortEvents are still stored, but 'iacMib.monitorStatus.
				shortEventStatus' is not set, resulting in that no monitor status message is
				sent."
			::= { iacMonitorSettings 6 }

		
		-- 1.3.6.1.4.1.5828.3.2.6.7
		nofBroadEventThresh OBJECT-TYPE
			SYNTAX Gauge
			ACCESS read-write
			STATUS mandatory
			DESCRIPTION
				"The number of broadEvent:s in 1 second required for the IAC to set
				'iacMib.monitorStatus.broadEventStatus' to NOK.
				If the 'broadEventStatus' in the IAC changes (either from OK to
				NOK, or from NOK to OK) it sends a monitor status message.
				
				If this MIB-variable is set to 0, this functionality is disabled. I.e within
				the IAC nofBroadEvents are still stored, but 'iacMib.monitorStatus.
				broadEventStatus' is not set, resulting in that no monitor status message is
				sent."
			::= { iacMonitorSettings 7 }

		
		-- 1.3.6.1.4.1.5828.3.2.6.8
		nofUnExpEventThresh OBJECT-TYPE
			SYNTAX Gauge
			ACCESS read-write
			STATUS mandatory
			DESCRIPTION
				"The number of unExpEvents in 1 second required for the IAC to set
				'iacMib.monitorStatus.unExpEventStatus' to NOK.
				If the 'unExpEventStatus' in the IAC changes (either from OK to
				NOK, or from NOK to OK) it sends a monitor status message.
				
				If this MIB-variable is set to 0, this functionality is disabled. I.e within
				the IAC nofUnExpEvents are still stored, but 'iacMib.monitorStatus.
				unExpEventStatus' is not set, resulting in that no monitor status message is
				sent."
			::= { iacMonitorSettings 8 }

		
-- IAC switch settings
		-- 1.3.6.1.4.1.5828.3.2.7
		iacSwitchSettings OBJECT IDENTIFIER ::= { iacRoot 7 }

		
		-- 1.3.6.1.4.1.5828.3.2.7.1
		switchMode OBJECT-TYPE
			SYNTAX INTEGER
				{
				open(0),
				dynamic(1),
				closed(2)
				}
			ACCESS read-write
			STATUS mandatory
			DESCRIPTION
				"Defines the mode of the returnswitch in the IAC.
				
				The default value is Dynamic."
			::= { iacSwitchSettings 1 }

		
		-- 1.3.6.1.4.1.5828.3.2.7.2
		fbMode OBJECT-TYPE
			SYNTAX OCTET STRING
			ACCESS read-write
			STATUS mandatory
			DESCRIPTION
				"Defines mode of filterbank 1, 2, 3, and 4 and switch source.
				
				Bit0
				Filterbank 1 - Active(1) or Inactive(0)
				
				Bit1
				Filterbank 2 - Active(1) or Inactive(0)
				
				Bit2
				Filterbank 3 - Active(1) or Inactive(0)
				
				Bit3
				Filterbank 4 - Active(1) or Inactive(0)
				
				Bit4
				switchSource - switchMod(0) or switchTP(1)
				The default switch, switchMod, is the unfiltered switch.
				The other switch, switchTP, is the filtered switch
				"
			::= { iacSwitchSettings 2 }

		
		-- 1.3.6.1.4.1.5828.3.2.7.3
		gainMode OBJECT-TYPE
			SYNTAX INTEGER
				{
				hw(0),
				low(1),
				high(2)
				}
			ACCESS read-write
			STATUS mandatory
			DESCRIPTION
				"Defines operational gain mode of the IAC.
				
				The default gain mode, HW, is gain controlled by HW jumper.
				LOW is SW controlled, low sensitivity.
				HIGH is SW controlled, high sensitivity."
			::= { iacSwitchSettings 3 }

		
-- IAC statistics settings
		-- 1.3.6.1.4.1.5828.3.2.8
		iacStatisticsSettings OBJECT IDENTIFIER ::= { iacRoot 8 }

		
		-- 1.3.6.1.4.1.5828.3.2.8.1
		statTimePeriodDef OBJECT-TYPE
			SYNTAX Gauge
			ACCESS read-write
			STATUS mandatory
			DESCRIPTION
				"Defines the length of the period during which statistics shall be calculated.
				The length of the period is given in hours, ranging from 1 to 254 hours.
				
				Setting this value to 0 disables the statistics.
				Setting this value to 255 results in continuous statistics."
			::= { iacStatisticsSettings 1 }

		
		-- 1.3.6.1.4.1.5828.3.2.8.2
		statResolutionDef OBJECT-TYPE
			SYNTAX Gauge
			ACCESS read-write
			STATUS mandatory
			DESCRIPTION
				"Defines the interval at which statistics is reported.
				The resolution is given in minutes, ranging from 1 to 255 minutes."
			::= { iacStatisticsSettings 2 }

		
		-- 1.3.6.1.4.1.5828.3.2.8.3
		statShortestEventDef OBJECT-TYPE
			SYNTAX Gauge
			ACCESS read-write
			STATUS mandatory
			DESCRIPTION
				"Defines the upper threshold for the shortest events. Events with a duration in
				the interval (0 - statShortestEventDef) us will fall into the shortest event 
				category.
				
				The range for this event definition is 0 to 65535 us."
			::= { iacStatisticsSettings 3 }

		
		-- 1.3.6.1.4.1.5828.3.2.8.4
		statShortEventDef OBJECT-TYPE
			SYNTAX Gauge
			ACCESS read-write
			STATUS mandatory
			DESCRIPTION
				"Defines the upper threshold for the short events. Events with a duration in 
				the interval (statShortestEventDef - statShortEventDef) us will fall into the 
				short event category.
				
				The range for this event definition is 0 to 65535 us."
			::= { iacStatisticsSettings 4 }

		
		-- 1.3.6.1.4.1.5828.3.2.8.5
		statLongEventDef OBJECT-TYPE
			SYNTAX Gauge
			ACCESS read-write
			STATUS mandatory
			DESCRIPTION
				"Defines the upper threshold for the middle events. Events with a duration in 
				the interval (statShortEventDef us - statLongEventDef ms) will fall into the 
				middle event category.
				
				The range for this event definition is 0 to 65535 ms."
			::= { iacStatisticsSettings 5 }

		
		-- 1.3.6.1.4.1.5828.3.2.8.6
		statLongestEventDef OBJECT-TYPE
			SYNTAX Gauge
			ACCESS read-write
			STATUS mandatory
			DESCRIPTION
				"Defines the upper threshold for the long events. Events with a duration in the
				interval (statLongEventDef - statLongestEventDef) ms will fall into the long 
				event category. 
				Events with a duration longer than statLongestEventDef will fall into longest 
				event category.
				
				The range for this event definition is 0 to 65535 ms."
			::= { iacStatisticsSettings 6 }

		
		-- 1.3.6.1.4.1.5828.3.2.8.7
		statAutoMode OBJECT-TYPE
			SYNTAX INTEGER
				{
				off(0),
				on(1)
				}
			ACCESS read-write
			STATUS mandatory
			DESCRIPTION
				"If automatic mode is enabled statistics records are sent in traps."
			::= { iacStatisticsSettings 7 }

		
-- IAC statistics records
		-- 1.3.6.1.4.1.5828.3.2.9
		iacStatisticsRecord OBJECT IDENTIFIER ::= { iacRoot 9 }

		
		-- 1.3.6.1.4.1.5828.3.2.9.1
		statRecSeqNumber OBJECT-TYPE
			SYNTAX Gauge
			ACCESS read-only
			STATUS mandatory
			DESCRIPTION
				"The sequence number is updated every time the statistics record is updated."
			::= { iacStatisticsRecord 1 }

		
		-- 1.3.6.1.4.1.5828.3.2.9.2
		statRecMaxDuration OBJECT-TYPE
			SYNTAX Gauge
			ACCESS read-only
			STATUS mandatory
			DESCRIPTION
				"The longest event detected during a resolution period (0..65535) ms."
			::= { iacStatisticsRecord 2 }

		
		-- 1.3.6.1.4.1.5828.3.2.9.3
		statRecMinDuration OBJECT-TYPE
			SYNTAX Gauge
			ACCESS read-only
			STATUS mandatory
			DESCRIPTION
				"The shortest event detected during a resolution period (0..65535) us."
			::= { iacStatisticsRecord 3 }

		
		-- 1.3.6.1.4.1.5828.3.2.9.4
		statRecAveDuration OBJECT-TYPE
			SYNTAX Gauge
			ACCESS read-only
			STATUS mandatory
			DESCRIPTION
				"The average duration of all events detected during a resolution period (0..65535) ms."
			::= { iacStatisticsRecord 4 }

		
		-- 1.3.6.1.4.1.5828.3.2.9.5
		statRecNofShortestEvents OBJECT-TYPE
			SYNTAX Gauge
			ACCESS read-only
			STATUS mandatory
			DESCRIPTION
				"The number of events with a duration between (0 - iacMib.statisticsSettings.statShortestEventDef)."
			::= { iacStatisticsRecord 5 }

		
		-- 1.3.6.1.4.1.5828.3.2.9.6
		statRecNofShortEvents OBJECT-TYPE
			SYNTAX Gauge
			ACCESS read-only
			STATUS mandatory
			DESCRIPTION
				"The number of events with a duration between
				(iacMib.statisticsSettings.statShortestEventDef - iacMib.statisticsSettings.statShortEventDef)."
			::= { iacStatisticsRecord 6 }

		
		-- 1.3.6.1.4.1.5828.3.2.9.7
		statRecNofMiddleEvents OBJECT-TYPE
			SYNTAX Gauge
			ACCESS read-only
			STATUS mandatory
			DESCRIPTION
				"The number of events with a duration between
				(iacMib.statisticsSettings.statShortEventDef - iacMib.statisticsSettings.statLongEventDef)."
			::= { iacStatisticsRecord 7 }

		
		-- 1.3.6.1.4.1.5828.3.2.9.8
		statRecNofLongEvents OBJECT-TYPE
			SYNTAX Gauge
			ACCESS read-only
			STATUS mandatory
			DESCRIPTION
				"The number of events with a duration between
				(iacMib.statisticsSettings.statLongEventDef - iacMib.statisticsSettings.statLongestEventDef)."
			::= { iacStatisticsRecord 8 }

		
		-- 1.3.6.1.4.1.5828.3.2.9.10
		statRecNofLongestEvents OBJECT-TYPE
			SYNTAX Gauge
			ACCESS read-only
			STATUS mandatory
			DESCRIPTION
				"The number of events with a duration longer than
				iacMib.statisticsSettings.statLongestEventDef."
			::= { iacStatisticsRecord 10 }

		
-- IAC pilot settings
		-- 1.3.6.1.4.1.5828.3.2.10
		iacPilotSettings OBJECT IDENTIFIER ::= { iacRoot 10 }

		
		-- 1.3.6.1.4.1.5828.3.2.10.1
		pilotFreq OBJECT-TYPE
			SYNTAX Gauge
			ACCESS read-write
			STATUS mandatory
			DESCRIPTION
				"Defines the pilot frequency wtih resolution 50 kHz
				
				The range for this event definition is 0 to 65535 50kHz."
			::= { iacPilotSettings 1 }

		
		-- 1.3.6.1.4.1.5828.3.2.10.2
		state OBJECT-TYPE
			SYNTAX INTEGER
				{
				off(0),
				on(1)
				}
			ACCESS read-write
			STATUS mandatory
			DESCRIPTION
				"Enables or disables the pilot frequency."
			::= { iacPilotSettings 2 }

		
-- IAC software download objects
		-- 1.3.6.1.4.1.5828.3.2.11
		iacUpGradeSettings OBJECT IDENTIFIER ::= { iacRoot 11 }

		
		-- 1.3.6.1.4.1.5828.3.2.11.1
		downLoad OBJECT-TYPE
			SYNTAX INTEGER
				{
				normal(0),
				failed(1),
				erasing(2),
				prog(3),
				verify(4),
				switch(5),
				mark(6)
				}
			ACCESS read-write
			STATUS mandatory
			DESCRIPTION
				"Used to start or stop a sw download procedure to the IAC.
				When set to Prog the FLASH will be erased for next free sector and
				the IAC will be ready for new SW.
				
				When the SW have been downloaded this variable should be set to Normal
				to gain normal operation again.
				
				Initially the variable is set to Normal.
				Once the download has been successful the variable shall be set to Normal.
				downLoad can only be set to normal(0) and prog(3), the other values can
				only be read."
			::= { iacUpGradeSettings 1 }

		
		-- 1.3.6.1.4.1.5828.3.2.11.2
		verification OBJECT-TYPE
			SYNTAX OCTET STRING
			ACCESS read-write
			STATUS mandatory
			DESCRIPTION
				"Verifies the downloaded SW with the selected Version.
				The four most significant bits are holding Release and
				the four least significant bits are holding Version.
				
				When the object is read an undefined value is returned."
			::= { iacUpGradeSettings 2 }

		
		-- 1.3.6.1.4.1.5828.3.2.11.3
		switch OBJECT-TYPE
			SYNTAX OCTET STRING
			ACCESS read-write
			STATUS mandatory
			DESCRIPTION
				"Switch to the selected SW version.
				The four most significant bits are holding Release and
				the four least significant bits are holding Version.
				
				When the object is read an undefined value is returned."
			::= { iacUpGradeSettings 3 }

		
		-- 1.3.6.1.4.1.5828.3.2.11.4
		mark OBJECT-TYPE
			SYNTAX OCTET STRING
			ACCESS read-write
			STATUS mandatory
			DESCRIPTION
				"Marks the selected SW version.
				The four most significant bits are holding Release and
				the four least significant bits are holding Version.
				
				When the object is read an undefined value is returned."
			::= { iacUpGradeSettings 4 }

		
		-- 1.3.6.1.4.1.5828.3.2.11.5
		codeSegment OBJECT-TYPE
			SYNTAX OCTET STRING
			ACCESS read-write
			STATUS mandatory
			DESCRIPTION
				"The codeSegment is used to transfer a portion of the firmware image for the IAC.
				Each portion transferred by this object is referred to as a line.
				
				Each line begins with the first character from an Intel HEX record line.
				The first character is therefore expected to be an ASCII ':'.
				
				Lines which do not begin with ':' are ignored.
				
				The remainder of the Intel HEX record line is then presented in the code
				segment in the binary form of the data.
				
				:0300300002337A1E is converted to 3A 03 00 30 00 02 33 7A 1E.
				
				When the object is read a zero length octet is returned."
			::= { iacUpGradeSettings 5 }

		
-- Sub-tree for IAC events
		-- 1.3.6.1.4.1.5828.3.2.12
		iacEvents OBJECT IDENTIFIER ::= { iacRoot 12 }

		
-- The compliance specification
		-- 1.3.6.1.4.1.5828.3.2.13
		serialNumber OBJECT-TYPE
			SYNTAX Gauge
			ACCESS read-only
			STATUS mandatory
			DESCRIPTION
				"The unique identity of the IAC. 
				The variable is set by the operator at installation time.
				The allowed range for the serial number is 1 - 79999999."
			::= { iacRoot 13 }

		
	
--
-- Trap definitions
--
	
-- IAC SNMPv1 traps
		statisticsRecEvent TRAP-TYPE 
			ENTERPRISE iacEvents
			VARIABLES { statRecSeqNumber, statRecMaxDuration, statRecMinDuration, statRecAveDuration, statRecNofShortestEvents, 
				statRecNofShortEvents, statRecNofMiddleEvents, statRecNofLongEvents, statRecNofLongestEvents }
			DESCRIPTION 
				"Trap containing statistics record."
			::=  1

		longEvent TRAP-TYPE 
			ENTERPRISE iacEvents
			VARIABLES { longEventStatus, nofLongEvents }
			DESCRIPTION 
				"Trap sent when the 'longEventStatus' in the IAC changes (either from OK to
				NOK, or from NOK to OK). 'longEventStatus' is NOK when the number of longEvents
				in 1 minute exceeds 'iacMib.monitorSettings.nofLongEventThresh'
				
				The trap contains the number of long events detected by the IAC.
				Long events are events longer than the threshold defined by 
				'iacMib.monitorSettings.longEventDef'."
			::=  2

		shortEvent TRAP-TYPE 
			ENTERPRISE iacEvents
			VARIABLES { shortEventStatus, nofShortEvents }
			DESCRIPTION 
				"Trap sent when the 'shortEventStatus' in the IAC changes (either from OK to
				NOK, or from NOK to OK). 'shortEventStatus' is NOK when the number of
				shortEvents in 1 second exceeds 'iacMib.monitorSettings.nofShortEventThresh'
				
				The trap contains the number of short events detected by the IAC.
				Short events are events shorter than the threshold defined by 
				'iacMib.monitorSettings.shortEventDef'."
			::=  3

		broadEvent TRAP-TYPE 
			ENTERPRISE iacEvents
			VARIABLES { broadEventStatus, nofBroadEvents }
			DESCRIPTION 
				"Trap sent when the 'broadEventStatus' in the IAC changes (either from OK to
				NOK, or from NOK to OK). 'broadEventStatus' is NOK when the number of
				broadEvents in 1 second exceeds 'iacMib.monitorSettings.nofBroadEventThresh'
				
				The trap contains the number of broad events detected by the IAC.
				Broad events are defined by 'iacMib.monitorSettings.broadEventDef'."
			::=  4

		unExpEvent TRAP-TYPE 
			ENTERPRISE iacEvents
			VARIABLES { unExpEventStatus, nofUnExpEvents }
			DESCRIPTION 
				"Trap sent when the 'unExpEventStatus' in the IAC changes (either from OK to
				NOK, or from NOK to OK). 'unExpEventStatus' is NOK when the number of
				unExpEvents in 1 second exceeds 'iacMib.monitorSettings.nofUnExpEventThresh'
				
				The trap contains the number of unExp events detected by the IAC.
				UnExp events are defined by 'iacMib.monitorSettings.unExpEventDef'."
			::=  5

		tampEvent TRAP-TYPE 
			ENTERPRISE iacEvents
			VARIABLES { tampStatus }
			DESCRIPTION 
				"Trap sent when the 'tampStatus' in the IAC changes (either from OK to
				NOK, or from NOK to OK)."
			::=  6

	
	END

--
-- TELESTE-IAC-MIB.mib
--
