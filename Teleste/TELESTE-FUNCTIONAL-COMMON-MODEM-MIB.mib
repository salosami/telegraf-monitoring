--
-- TELESTE-FUNCTIONAL-COMMON-MODEM-MIB.mib
-- MIB generated by MG-SOFT Visual MIB Builder 2021 (64-bit) Version 15.00  Build 1510
-- Friday, August 27, 2021 at 10:52:00
--

-- ****************************************************************************
-- Copyright (c) 2003-2014 by:
-- 
-- Teleste Corporation
-- Seponkatu 1
-- FIN-20660 Littoinen, Finland
-- tel. +358 2 2605 611
-- url: http://www.teleste.com
-- 
-- Module Name: TELESTE-FUNCTIONAL-COMMON-MODEM-MIB
-- 
-- Description: MIB module describing common objects for a 
--              modem in any Teleste transponder
-- 
-- Revision History:
-- -----------------
-- 6, 24.8.2021, Sami Kuusisto
-- - Added new enum (commonModemConnectionStateModemNotInstalled(3)) to commonModemConnectionState.
-- 
-- 5, 11.2.2015, Sami Kuusisto
-- - Added new functionalModemProtocolRis(4) RIS to commonModemProtocol.
-- 
-- 4, 5.6.2014, Sami Kuusisto
-- - Changed packet statistics values from integer to counter. 
-- - Added value ranges.
-- 
-- 3, 18.3.2014, Sami Kuusisto
-- - Changed enumerations of commonModemRegState
-- - Added commonModemTxLevelStatus
-- 
-- 2, 18.3.2014, Sami Kuusisto
-- - Added commonModemConnectionState
-- 
-- 1, 11.3.2014, Sami Kuusisto
-- - Initial version
-- 
-- ****************************************************************************

	TELESTE-FUNCTIONAL-COMMON-MODEM-MIB DEFINITIONS ::= BEGIN
 
		IMPORTS
			OBJECT-TYPE			
				FROM RFC-1212			
			Counter			
				FROM RFC1155-SMI			
			functionalModuleId			
				FROM TELESTE-FUNCTIONAL-MODULE-MIB			
			functional			
				FROM TELESTE-ROOT-MIB;
	
	
	
--
-- Node definitions
--
	
		-- 1.3.6.1.4.1.3715.100.7
		commonModem OBJECT IDENTIFIER ::= { functional 7 }

		
-- Transponder RF modem specific objects
-- 
		-- 1.3.6.1.4.1.3715.100.7.1
		commonModemStatus OBJECT IDENTIFIER ::= { commonModem 1 }

		
		-- 1.3.6.1.4.1.3715.100.7.1.1
		commonModemRxLevel OBJECT-TYPE
			SYNTAX INTEGER (0..15000)
			ACCESS read-only
			STATUS mandatory
			DESCRIPTION
				"Modem receive level. 
				Unit 0.01 dBuV."
			::= { commonModemStatus 1 }

		
		-- 1.3.6.1.4.1.3715.100.7.1.2
		commonModemRxFrequency OBJECT-TYPE
			SYNTAX INTEGER (0..200000000)
			ACCESS read-only
			STATUS mandatory
			DESCRIPTION
				"Modem receive frequency.
				Unit 1 kHz."
			::= { commonModemStatus 2 }

		
		-- 1.3.6.1.4.1.3715.100.7.1.3
		commonModemTxFrequency OBJECT-TYPE
			SYNTAX INTEGER (0..200000000)
			ACCESS read-only
			STATUS mandatory
			DESCRIPTION
				"Modem transmit frequency. 
				Unit 1 kHz."
			::= { commonModemStatus 3 }

		
		-- 1.3.6.1.4.1.3715.100.7.1.4
		commonModemTxLevel OBJECT-TYPE
			SYNTAX INTEGER (0..20000)
			ACCESS read-write
			STATUS mandatory
			DESCRIPTION
				"Current modem transmit level. Unit 0.01 dBµV.
				Value range:
				- maximum is limited by the current modemTxLevelMax
				- minimum value is limited by the modem hardware"
			::= { commonModemStatus 4 }

		
		-- 1.3.6.1.4.1.3715.100.7.1.5
		commonModemTxLevelStatus OBJECT-TYPE
			SYNTAX INTEGER
				{
				commonModemTxLevelStatusOk(1),
				commonModemTxLevelStatusSaturated(2)
				}
			ACCESS read-only
			STATUS mandatory
			DESCRIPTION
				"Modem transmit level state. 
				1: tx level ok, 
				2: tx level saturated"
			::= { commonModemStatus 5 }

		
		-- 1.3.6.1.4.1.3715.100.7.1.6
		commonModemRegState OBJECT-TYPE
			SYNTAX INTEGER
				{
				commonModemRegState1(1),
				commonModemRegState2(2),
				commonModemRegState3(3),
				commonModemRegState4(4),
				commonModemRegState5(5),
				commonModemRegState6(6),
				commonModemRegState7(7),
				commonModemRegState8(8),
				commonModemRegState9(9),
				commonModemRegState10(10),
				commonModemRegState11(11),
				commonModemRegState12(12),
				commonModemRegState13(13)
				}
			ACCESS read-only
			STATUS mandatory
			DESCRIPTION
				"Modem registration state.
				
				CATVisor/HMS modem
				1: Reset
				2: Set receiver hardware to be ready
				3: Wait anypacket
				4: Wait RCD
				5: Transmitter setup time
				6: Set transmit level to hardware
				7: Send registration request
				8: Registration backoff time
				9: Wait registration acknowledgement
				10: Make status packet
				11: Connected/normal mode
				
				DOCSIS
				1: Other
				2: Not ready
				3: Not synchronized
				4: PHY synchronized
				5: US parameters acquired
				6: Ranging complete
				7: IP complete
				8: ToD established
				9: Security established
				10: Parameter transfer complete
				11: Registration complete
				12: Operational
				13: Access denied"
			::= { commonModemStatus 6 }

		
		-- 1.3.6.1.4.1.3715.100.7.1.7
		commonModemConnectionState OBJECT-TYPE
			SYNTAX INTEGER
				{
				commonModemConnectionStateConnected(1),
				commonModemConnectionStateNotConnected(2),
				commonModemConnectionStateModemNotInstalled(3)
				}
			ACCESS read-only
			STATUS mandatory
			DESCRIPTION
				"Modem connection state.
				1: Modem is connected.
				2: Modem is not connected.
				3: Modem not installed."
			::= { commonModemStatus 7 }

		
		-- 1.3.6.1.4.1.3715.100.7.1.8
		commonModemProtocol OBJECT-TYPE
			SYNTAX INTEGER
				{
				functionalModemProtocolCATVisor(1),
				functionalModemProtocolHms(2),
				functionalModemProtocolDocsis(3),
				functionalModemProtocolRis(4)
				}
			ACCESS read-write
			STATUS mandatory
			DESCRIPTION
				"Modem protocol in use.
				Writing this object resets the unit and changes the protocol
				and may thus cause loss of remote connection.
				All communication settings should be reviewed carefully
				before writing this object.
				1 = CATVisor (Teleste proprietary 'TSEMP') protocol
				2 = HMS protocol
				3 = DOCSIS"
			::= { commonModemStatus 8 }

		
-- Transponder modem statistics objects.
		-- 1.3.6.1.4.1.3715.100.7.2
		commonModemPacketStatistics OBJECT IDENTIFIER ::= { commonModem 2 }

		
		-- 1.3.6.1.4.1.3715.100.7.2.1
		commonModemPacketStatisticsReceived OBJECT-TYPE
			SYNTAX Counter
			ACCESS read-only
			STATUS mandatory
			DESCRIPTION
				"Number of received packets (MAC + payload))"
			::= { commonModemPacketStatistics 1 }

		
		-- 1.3.6.1.4.1.3715.100.7.2.2
		commonModemPacketStatisticsBad OBJECT-TYPE
			SYNTAX Counter
			ACCESS read-only
			STATUS mandatory
			DESCRIPTION
				"Number of received packets declared as bad."
			::= { commonModemPacketStatistics 2 }

		
		-- 1.3.6.1.4.1.3715.100.7.2.3
		commonModemPacketStatisticsSent OBJECT-TYPE
			SYNTAX Counter
			ACCESS read-only
			STATUS mandatory
			DESCRIPTION
				"Number of sent packets."
			::= { commonModemPacketStatistics 3 }

		
		-- 1.3.6.1.4.1.3715.100.7.2.4
		commonModemPacketStatisticsReset OBJECT-TYPE
			SYNTAX INTEGER { reset(1) }
			ACCESS read-write
			STATUS mandatory
			DESCRIPTION
				"Write only variable for resetting the modem packet
				statistics counters. A get operation returns always value 1."
			::= { commonModemPacketStatistics 4 }

		
		-- 1.3.6.1.4.1.3715.100.7.3
		commonModemReturnPathModemInputLevelTable OBJECT-TYPE
			SYNTAX SEQUENCE OF CommonModemReturnPathModemInputLevelEntry
			ACCESS not-accessible
			STATUS mandatory
			::= { commonModem 3 }

		
		-- 1.3.6.1.4.1.3715.100.7.3.1
		commonModemReturnPathModemInputLevelEntry OBJECT-TYPE
			SYNTAX CommonModemReturnPathModemInputLevelEntry
			ACCESS not-accessible
			STATUS mandatory
			INDEX { functionalModuleId }
			::= { commonModemReturnPathModemInputLevelTable 1 }

		
		CommonModemReturnPathModemInputLevelEntry ::=
			SEQUENCE { 
				commonModemReturnPathModemInputLevel
					INTEGER
			 }

		-- 1.3.6.1.4.1.3715.100.7.3.1.1
		commonModemReturnPathModemInputLevel OBJECT-TYPE
			SYNTAX INTEGER (0..20000)
			ACCESS read-write
			STATUS mandatory
			DESCRIPTION
				"Modem equivalent input level.
				 	
				The signal level needed at return path input to appear at same level 
				than modem transmit signal at return path output. 
				
				Unit 0.01 dBµV"
			::= { commonModemReturnPathModemInputLevelEntry 1 }

		
	
	END

--
-- TELESTE-FUNCTIONAL-COMMON-MODEM-MIB.mib
--
