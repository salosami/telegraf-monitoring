--
-- TELESTE-FUNCTIONAL-LEVEL-CONTROL-MIB.mib
-- MIB generated by MG-SOFT Visual MIB Builder 2013 (64-bit) Version 9.0  Build 760
-- Wednesday, March 23, 2016 at 12:39:27
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-LEVEL-CONTROL-MIB
-- 
-- Description:   MIB module describing Teleste functional level control interface specific objects
-- 
-- Revision history:
-- -----------------
-- 6, 23.3.2016, Sami Kuusisto
-- - Changed levelControlMinimumValue, levelControlMaximumValue as RO.
-- 
-- 5, 5.6.2014, Sami Kuusisto
-- - Added value ranges.
-- 
-- 4, 16.5.2014, Sami Kuusisto
-- - Added levelControlMinimumValue and levelControlMaximumValue.
-- 
-- 3, 19.3.2014, Sami Kuusisto
-- - Updated levelControlStep description: read returns levelControlValue.
-- 
-- 2, 14.3.2014, Sami Kuusisto
-- - removed levelControlType. Similar information is available at functionalModuleName.
-- 
-- 1, 10.3.2014, Sami Kuusisto
-- - Initial version.
-- 
-- ****************************************************************************
-- 

	TELESTE-FUNCTIONAL-LEVEL-CONTROL-MIB DEFINITIONS ::= BEGIN
 
		IMPORTS
			OBJECT-TYPE			
				FROM RFC-1212			
			functionalModuleId			
				FROM TELESTE-FUNCTIONAL-MODULE-MIB			
			functional			
				FROM TELESTE-ROOT-MIB;
	
	
	
--
-- Node definitions
--
	
		-- 1.3.6.1.4.1.3715.100.71
		levelControl OBJECT IDENTIFIER ::= { functional 71 }

		
		-- 1.3.6.1.4.1.3715.100.71.1
		levelControlTable OBJECT-TYPE
			SYNTAX SEQUENCE OF LevelControlEntry
			ACCESS not-accessible
			STATUS mandatory
			DESCRIPTION
				"A table of level control elements (gain and slope)."
			::= { levelControl 1 }

		
		-- 1.3.6.1.4.1.3715.100.71.1.1
		levelControlEntry OBJECT-TYPE
			SYNTAX LevelControlEntry
			ACCESS not-accessible
			STATUS mandatory
			INDEX { functionalModuleId }
			::= { levelControlTable 1 }

		
		LevelControlEntry ::=
			SEQUENCE { 
				levelControlValue
					INTEGER,
				levelControlStatus
					INTEGER,
				levelControlStepSize
					INTEGER,
				levelControlStep
					INTEGER,
				levelControlMinimumValue
					INTEGER,
				levelControlMaximumValue
					INTEGER
			 }

		-- 1.3.6.1.4.1.3715.100.71.1.1.1
		levelControlValue OBJECT-TYPE
			SYNTAX INTEGER
			ACCESS read-write
			STATUS mandatory
			DESCRIPTION
				"Level control value. Unit 0.01 dB. 
				
				The value may be read-only when ALSC is switched on.
				"
			::= { levelControlEntry 1 }

		
		-- 1.3.6.1.4.1.3715.100.71.1.1.2
		levelControlStatus OBJECT-TYPE
			SYNTAX INTEGER
				{
				normal(1),
				minimum(2),
				maximum(3),
				frozen(4),
				default(5),
				saturatedAtMinimum(6),
				saturatedAtMaximum(7),
				unknown(8)
				}
			ACCESS read-only
			STATUS mandatory
			DESCRIPTION
				"Level control status:
				1: normal
				2: minimum (control at minimum, but no request to adjust under minimum)
				3: maximum (control at maximum, but no request to adjust over maximum)
				4: frozen (not used)
				5: default (not used)
				6: saturatedAtMinimum (control saturated at minimum value, but there's need to adjust under minimum)
				7: saturatedAtMaximum (control saturated at maximum value, but there's need to adjust over maximum)
				8: unknown"
			::= { levelControlEntry 2 }

		
		-- 1.3.6.1.4.1.3715.100.71.1.1.3
		levelControlStepSize OBJECT-TYPE
			SYNTAX INTEGER (0..10000)
			ACCESS read-only
			STATUS mandatory
			DESCRIPTION
				"Level control element step size.
				Unit 0.01 dB."
			::= { levelControlEntry 3 }

		
		-- 1.3.6.1.4.1.3715.100.71.1.1.4
		levelControlStep OBJECT-TYPE
			SYNTAX INTEGER
			ACCESS read-write
			STATUS mandatory
			DESCRIPTION
				"Write:
				Level control element step command.
				Value is number of steps to be stepped. Device performs step*stepSize step in decibels.
				If step < 0, element steps towards minimum.
				If step > 0, element steps towards maximum.
				
				Read: 
				levelControlValue (unit 0.01 dB) after step commands. 
				So there's no need to read levelControlValue after step command to get the current value."
			::= { levelControlEntry 4 }

		
		-- 1.3.6.1.4.1.3715.100.71.1.1.5
		levelControlMinimumValue OBJECT-TYPE
			SYNTAX INTEGER
			ACCESS read-only
			STATUS mandatory
			::= { levelControlEntry 5 }

		
		-- 1.3.6.1.4.1.3715.100.71.1.1.6
		levelControlMaximumValue OBJECT-TYPE
			SYNTAX INTEGER
			ACCESS read-only
			STATUS mandatory
			::= { levelControlEntry 6 }

		
	
	END

--
-- TELESTE-FUNCTIONAL-LEVEL-CONTROL-MIB.mib
--
