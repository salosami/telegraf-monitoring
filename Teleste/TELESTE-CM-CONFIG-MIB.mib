--
-- TELESTE-CM-CONFIG-MIB.mib
-- MIB generated by MG-SOFT Visual MIB Builder 2020 (64-bit) Version 14.00  Build 1400
-- Friday, January 10, 2020 at 12:51:40
--

-- *****************************************************************************
-- Copyright (c) 2011
-- 
-- Teleste Corporation
-- Seponkatu 1
-- FIN-20660 Littoinen, Finland
-- tel. +358 2 2605 611
-- http://www.teleste.com/
-- 
-- Description: Cable modem configuration MIB for Teleste transponders
-- 
-- Revision History:
-- -----------------
-- v6 10.1.2020 Sami Kuusisto
-- - Added original docsIfDownChannelPower to cmDynamicParameterRecord.
-- 
-- v5 19.9.2017 Sami Kuusisto
-- - Added cmAmpMRU, cmAmpMTU and cmIPv6Address.
-- 
-- v4 19.9.2013 Sami Kuusisto
-- - Added cmWatchdogTimeout
-- 
-- v3 26.1.2012 Sami Halen
-- - Changed cmConfig root from functional.7 to functional.999 (now imported from root)
-- - Added cmSerialNumber to cmStaticParameterRecord
-- - Added descriptions to cmDynamicParameterRecord fields
-- 
-- v2  16.12.2011 Sami Halen
-- - Changes based on comments
-- 
-- v1  14.12.2011 Sami Halen
-- - First draft
-- 
-- ****************************************************************************
-- 

	TELESTE-CM-CONFIG-MIB DEFINITIONS ::= BEGIN
 
		IMPORTS
			OBJECT-TYPE			
				FROM RFC-1212			
			cmConfig			
				FROM TELESTE-ROOT-MIB;
	
	
--
-- Node definitions
--
	
		-- 1.3.6.1.4.1.3715.100.999.1
		cmParamRangeTable OBJECT-TYPE
			SYNTAX SEQUENCE OF CmParamRangeEntry
			ACCESS not-accessible
			STATUS mandatory
			DESCRIPTION
				"Table containing parameter (OID) ranges supported by the device."
			::= { cmConfig 1 }

		
		-- 1.3.6.1.4.1.3715.100.999.1.1
		cmParamRangeEntry OBJECT-TYPE
			SYNTAX CmParamRangeEntry
			ACCESS not-accessible
			STATUS mandatory
			INDEX { cmParamRangeIndex }
			::= { cmParamRangeTable 1 }

		
		CmParamRangeEntry ::=
			SEQUENCE { 
				cmParamRangeIndex
					INTEGER,
				cmParamRangeStartOid
					OBJECT IDENTIFIER,
				cmParamRangeEndOid
					OBJECT IDENTIFIER
			 }

		-- 1.3.6.1.4.1.3715.100.999.1.1.1
		cmParamRangeIndex OBJECT-TYPE
			SYNTAX INTEGER (1..10)
			ACCESS read-only
			STATUS mandatory
			DESCRIPTION
				"Unique index of cmParamRange"
			::= { cmParamRangeEntry 1 }

		
		-- 1.3.6.1.4.1.3715.100.999.1.1.2
		cmParamRangeStartOid OBJECT-TYPE
			SYNTAX OBJECT IDENTIFIER
			ACCESS read-only
			STATUS mandatory
			DESCRIPTION
				"First supported parameter (OID) in the range"
			::= { cmParamRangeEntry 2 }

		
		-- 1.3.6.1.4.1.3715.100.999.1.1.3
		cmParamRangeEndOid OBJECT-TYPE
			SYNTAX OBJECT IDENTIFIER
			ACCESS read-only
			STATUS mandatory
			DESCRIPTION
				"Last supported parameter (OID) in the range."
			::= { cmParamRangeEntry 3 }

		
		-- 1.3.6.1.4.1.3715.100.999.2
		cmDynamicParameterRecord OBJECT-TYPE
			SYNTAX OCTET STRING
			ACCESS read-write
			STATUS mandatory
			DESCRIPTION
				"Record containing dynamic cable modem data:
				(format uint32 / network byte order unless otherwise noted)
				docsIfDownChannelFrequency (Rx center frequency in Hz, as in 1.3.6.1.2.1.10.127.1.1.1.1.2)
				docsIfDownChannelQamMode  (Rx modulation type, as in 1.3.6.1.2.1.10.127.1.1.1.1.4)
				docsIfDownChannelPower (Rx power in 0.1 dBmV, as in 1.3.6.1.2.1.10.127.1.1.1.1.6): CM reports to this docsIfDownChannelPower but amplifier adds offset to this.
				docsIfSigQSignalNoise (Rx S/N ratio in 0.1 dB, as in 1.3.6.1.2.1.10.127.1.1.4.1.5)
				docsIfUpChannelId (Tx CMTS identification, as in 1.3.6.1.2.1.10.127.1.1.2.1.1)
				docsIfUpChannelFrequency (Tx center frequency in Hz, as in 1.3.6.1.2.1.10.127.1.1.2.1.2)
				docsIfUpChannelBandwidth (Tx bandwidth in Hz, as in 1.3.6.1.2.1.10.127.1.1.2.1.3)
				docsIfCmStatusTxPower (Tx power in 0.1 dBmV, as in 1.3.6.1.2.1.10.127.1.1.1.1.6)
				docsIfCmStatusValue (CM communication status, as in 1.3.6.1.2.1.10.127.1.2.2.1.1)
				cmSystemTime (System POSIX time, MSB first)
				cmIfAddress (format: IpAddress)
				docsIfDownChannelPower (original value received from CM; only new amplifier softwares supports this field)"
			::= { cmConfig 2 }

		
		-- 1.3.6.1.4.1.3715.100.999.3
		cmStaticParameterRecord OBJECT-TYPE
			SYNTAX OCTET STRING
			ACCESS read-write
			STATUS mandatory
			DESCRIPTION
				"Record containing static cable modem data:
				cmPhysAddress (octet string [6])
				cmSwVersion (string; len (1 octet) + swversion (len octets), len max 15)
				cmHwVersion (string; len (1 octet) + hwversion (len octets), len max 15)
				cmSerialNumber (string; len (1 octet) + serialnumber (len octets), len max 15)"
			::= { cmConfig 3 }

		
		-- 1.3.6.1.4.1.3715.100.999.4
		cmWatchdogTimeout OBJECT-TYPE
			SYNTAX INTEGER
			ACCESS read-write
			STATUS mandatory
			DESCRIPTION
				"CM watchdog timeout. If docsIfCmStatusValue in cmDynamicParameterRecord 
				is not 'operational(12)' within timeout minutes, CM is reinitialised.
				Unit 1 minute. Value 0 disables CM watchdog."
			::= { cmConfig 4 }

		
		-- 1.3.6.1.4.1.3715.100.999.5
		cmAmpMRU OBJECT-TYPE
			SYNTAX INTEGER
			ACCESS read-only
			STATUS mandatory
			DESCRIPTION
				"Maximum packet size that amplifier can receive from cable modem.
				 
				This value contais payload and headers.
				
				E.g. Legacy HMS: SNMP payload (UDP datagram) (484 bytes), UDP header (8 bytes), IPv4 header (20 bytes): 512 bytes.
				
				If amplifier doesn't support this OID, then default (and legacy) MRU is used: 512 bytes.
				"
			::= { cmConfig 5 }

		
		-- 1.3.6.1.4.1.3715.100.999.6
		cmAmpMTU OBJECT-TYPE
			SYNTAX INTEGER
			ACCESS read-only
			STATUS mandatory
			DESCRIPTION
				"Maximum packet size that amplifier can transmit to cable modem.
				 
				This value contais payload and headers.
				
				E.g. Legacy HMS: SNMP payload (UDP datagram) (484 bytes), UDP header (8 bytes), IPv4 header (20 bytes): 512 bytes.
				
				If amplifier doesn't support this OID, then default (and legacy) MTU is used: 512 bytes."
			::= { cmConfig 6 }

		
		-- 1.3.6.1.4.1.3715.100.999.7
		cmIPv6address OBJECT-TYPE
			SYNTAX OCTET STRING
			ACCESS read-write
			STATUS mandatory
			DESCRIPTION
				"Public IPv6 address of CM as text string: ffff:ffff:ffff:ffff:ffff:ffff:ffff:ffff"
			::= { cmConfig 7 }

		
	
	END

--
-- TELESTE-CM-CONFIG-MIB.mib
--
