--
-- TELESTE-FUNCTIONAL-NODE-RETURN-PATH-MIB.mib
-- MIB generated by MG-SOFT Visual MIB Builder 2013 (64-bit) Version 9.0  Build 760
-- Wednesday, March 12, 2014 at 16:06:12
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-NODE-PATH-MIB
-- 
-- Description:   MIB module describing Teleste functional node return path interface specific objects
-- 
-- Revision history:
-- -----------------
-- 1, 12.3.2014, Sami Kuusisto
-- - Initial version.
-- 
-- ****************************************************************************
-- 

	TELESTE-FUNCTIONAL-NODE-RETURN-PATH-MIB DEFINITIONS ::= BEGIN
 
		IMPORTS
			OBJECT-TYPE			
				FROM RFC-1212			
			functional			
				FROM TELESTE-ROOT-MIB;
	
	
	
--
-- Node definitions
--
	
		-- 1.3.6.1.4.1.3715.100.53
		nodeReturnPath OBJECT IDENTIFIER ::= { functional 53 }

		
		-- 1.3.6.1.4.1.3715.100.53.1
		nodeReturnPathLaserActivity OBJECT-TYPE
			SYNTAX INTEGER
				{
				laserBothActive(1),
				laserFollowSignalRelay(2),
				laserNotAvailable(3)
				}
			ACCESS read-write
			STATUS mandatory
			DESCRIPTION
				"Optical return transmitter mode:
				1 = both active
				2 = only selected TX is active (follows signal relay position)
				3 = there is no return transmitter installed"
			::= { nodeReturnPath 1 }

		
	
	END

--
-- TELESTE-FUNCTIONAL-NODE-RETURN-PATH-MIB.mib
--
