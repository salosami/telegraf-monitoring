--
-- TELESTE-ACX-MIB.mib
-- MIB generated by MG-SOFT Visual MIB Builder 2021 (64-bit) Version 15.00  Build 1510
-- Thursday, May 12, 2022 at 09:18:53
--

-- ****************************************************************************
-- Copyright (c) 2003-2012 by:
-- 
-- Teleste Corporation
-- Seponkatu 1
-- FIN-20660 Littoinen, Finland
-- tel. +358 2 2605 611
-- url: http://www.teleste.com
-- 
-- Module Name:   TELESTE-ACX-MIB
-- 
-- Description:   MIB module describing Teleste ACcess family specific objects
-- 
-- Revision history:
-- -----------------
-- 112, 12.5.2022, Sami Kuusisto
-- - Added enum acxPsu1/2StatusConnectionLost to acxPsu1/2Status.
-- 
-- 111, 9.5.2022, Sami Kuusisto
-- - Added acx12VPsu2 and added LuminatoPSU type/enum to acxPsu1/2Type.
-- 
-- 110, 7.12.2021, Sami Kuusisto
-- - Added acxSupplyVoltageCrestFactor and acxSupplyVoltagePeakValue.
-- 
-- 109, 17.6.2021, Sami Kuusisto
-- - Added enum powersaveRfLaser(5) to acxReturnPathPowerSave.
-- 
-- 108, 4.12.2020, Sami Kuusisto
-- - Added ac9400rpInputToOptTxSlotMapping.
-- 
-- 107, 22.4.2020, Sami Kuusisto
-- - Added enum NA(4) to acxActiveOpticalInput and acxOpticalInputControl.
-- 
-- 106, 21.2.2020, Sami Kuusisto
-- - Added AC3080 and AC3280 sysOIDs.
-- 
-- 105, 27.1.2020, Sami Kuusisto
-- - Added AC8710 and AC8810 generations: 1st and 2nd gen.
-- 
-- 104, 24.10.2019, Sami Kuusisto
-- - Changed ac9400output12ModuleType and ac9400output34ModuleType enumerations.
-- 
-- 103, 2.10.2019, Sami Kuusisto
-- - Updated ac9100alc3FollowsAlc1 and ac9100alc3OffsetToAlc1 description: added AC9400 to products that supports feature.
-- 
-- 102, 13.9.2019, Sami Kuusisto
-- - Added acx34VPsu1 and acx34VPsu2.
-- 
-- 101, 7.6.2019, Sami Kuusisto
-- - Renamed ac3010rpc, ac3020rpc and ac3210rpc to ac3010irpc, ac3020irpc and ac3210irpc.
-- 
-- 100, 3.6.2019, Sami Kuusisto
-- - Renamed ac3010rlsc, ac3020rlsc and ac3210rlsc to ac3010rpc, ac3020rpc and ac3210rpc.
-- 
-- 99, 27.5.2019, Sami Kuusisto
-- - Added ac3010rlsc, ac3020rlsc and ac3210rlsc.
-- 
-- 98, 13.3.2019, Sami Kuusisto
-- - Added ac9400output12ModuleType and ac9400output34ModuleType. Reserved AC9400 generations OID.
-- 
-- 97, 8.3.2019, Sami Kuusisto
-- - Added AC9400 sysOID.
-- 
-- 96, 14.2.2019, Sami Kuusisto
-- - Added acxLevelDetectorSupportedModes.
-- 
-- 95, 13.2.2019, Sami Kuusisto
-- - Added new enums (minHold(6) and maxHold(6) to acxLevelDetectorMode.
-- 
-- 94, 11.1.2019, Sami Kuusisto
-- - Added new enumerations ingressSwitchControlModeAlarmOff(3) and ingressSwitchControlModeWarningAttenuateAlarmOff(4) to acxIngressSwitchControlMode.
-- - Added new OID acxIngressSwitchControlModeVersion.
-- 
-- 93, 30.10.2018, Sami Kuusisto
-- - Added ac3010-generations (due ac3010-3rdgen) and ac3210-3rdgen.
--  
-- 92, 10.10.2018, Sami Kuusisto
-- - Added acxOpticalReceiverOpticalPowerMinLevel and acxOpticalReceiverOpticalPowerMaxLevel.
-- 
-- 91, 1.10.2018, Sami Kuusisto
-- - Added new enums (annexB(4), OFDM(5), unset(16) to acxLevelDetectorMode.
-- 
-- 90, 9.5.2018, Sami Kuusisto
-- - Added new enums (42/53, 117/47, FDX) to acxReturnPathBand.
-- 
-- 89, 3.5.2018, Sami Kuusisto
-- - Added AC3020 sysOID (and copy&paste ac3010 subOIDs).
-- 
-- 88, 26.4.2018, Sami Kuusisto
-- - Added controlOutput(6) to acxLevelControlType.
-- 
-- 87, 24.4.2018, Sami Kuusisto
-- - Added acxOpticalReceiverAnalogOffsetMin/Max/StepSize
-- 
-- 86, 28.3.2018, Sami Kuusisto
-- - Added ac9100alc3OffsetToAlc1.
-- 
-- 85, 27.3.2018, Sami Kuusisto
-- - Added ac9100alc3FollowsAlc1.
-- 
-- 84, 22.3.2018, Sami Kuusisto
-- - Added acxReturnTransmitterStatus.
-- 
-- 83, 7.3.2018, Sami Kuusisto
-- - Added acxOpticalReveicerOlcOffset and acxOpticalReceiverAnalogOffset.
-- 
-- 82, 1.12.2017, Sami Kuusisto
-- - Added acxReturnTransmitterItuChannel.
-- 
-- 81, 24.11.2017, Sami Kuusisto
-- - Added acxSupplyVoltageRMS2.
-- 
-- 80, 20.09.2017, Sami Kuusisto
-- - Added acxPsu1Type and acxPsu2Type.
-- 
-- 79, 08.09.2017, Sami Kuusisto
-- - Added acxPsu1Status and acxPsu2Status.
-- 
-- 78, 23.05.2017, Sami Kuusisto
-- - Added RF3(bit 2) to acxForwardPathOutputEnable.
-- 
-- 77, 09.05.2017, Sami Kuusisto
-- - Added ac3210-2ndgen
-- 
-- 76, 16.02.2017, Sami Kuusisto
-- - Added acxBackupStatus.
-- 
-- 75, 03.02.2017, Sami Kuusisto
-- - Renamed sysOID ac9100neo to ac9100NEO.
-- 
-- - 74, 01.02.2017, Sami Kuusisto
-- - Renamed AC9200 to AC9100 NEO in acxReturnPathRoutingControl description.
-- 
-- 73, 27.01.2017, Sami Kuusisto
-- - Renamed AC9200 to AC9100neo and changed sysOID from 9200 to 9100.2
-- - Renamed ac9200ReturnPathRfSplit to ac9100neoReturnPathRfSplit and changed oid accordingly.
-- 
-- 72, 18.01.2017, Sami Kuusisto
-- - Added AC9200 sysOID and ac9200ReturnPathRfSplit (under AC9200).
-- 
-- 71, 16.12.2016, Sami Kuusisto
-- - Added modes 21 and 22 to acxReturnPathRoutingStatus. Added modes 11 and 12 to acxReturnPathRoutingControl.
-- 
-- 70, 31.8.2016, Sami Kuusisto
-- - Fixed typo in acxReturnPathOmiTestPointControl description: tx2 and tx3 descriptions were mixed.
-- 
-- 69, 15.6.2016, Sami Kuusisto
-- - Added acxReturnPathOmiTestPointControl.
-- 
-- 68, 2.5.2016, Sami Kuusisto
-- - Added mode 10 to acxReturnPathRoutingControl. Renamed states to mode1-10.
-- 
-- 67, 20.04.2016, Sami Kuusisto
-- - Added enum 13 (rf1rf2rf3rf4tx1only1laserOn) to acxReturnPathRoutingControl.
-- 
-- 66, 19.04.2016, Sami Kuusisto
-- - Added RF+laser2 powersave mode (enum 4) to acxReturnPathPowerSave.
-- - Renamed RF+laser to RF+laser1 (enum 3) (acxReturnPathPowerSave).
-- 
-- 65, 1.10.2015, Sami Kuusisto
-- - Added (AC3x10): ac3x10preSlope1GHz, ac3x10trunkDistributionSelection and ac3010inputBypassOutput3Selection.
-- 
-- 64, 25.6.2015, Sami Kuusisto
-- - Added AC3010 and AC3210 sysOIDs.
-- 
-- 63, 24.2.2015, Sami Kuusisto
-- - Added mode 8 (RF1->Tx1, RF2->RF2, RF3->Tx3, RF4->Tx4) to acxReturnPathRoutingControl.
-- - Added state 19 (RF1+RF2 to Tx2, RF3 to Tx3, RF4 to Tx4) to acxReturnPathRoutingStatus.
-- - Added state 20 (RF1 to Tx1, RF2 to Tx2, RF3+RF4 to Tx4) to acxReturnPathRoutingStatus.
-- 
-- 62, 23.2.2015, Sami Kuusisto
-- - Added mode 7 (RF1+RF2->Tx1, RF3->Tx3, RF4->Tx4) to acxReturnPathRoutingControl.
-- - Added state 18 (RF1+RF2 to Tx1, RF3 to Tx3, RF4 to Tx4) to acxReturnPathRoutingStatus.
-- 
-- 61, 9.10.2014, Sami Kuusisto
-- - Added AC9100, AC8710 and AC8810 sysOIDs.
-- 
-- 60, 24.3.2014, Sami Kuusisto
-- - Changed sysOIDs AC1000T3 (1003) to AC1500 (1500) and AC2000T2 (2003) to AC2500 (2500).
-- 
-- 
-- 59, 13.3.2014, Sami Kuusisto
-- - fixed acxForwardPathBand enum from band1206MHz to band1218MHz.
-- 
-- 58, 13.3.2014, Sami Kuusisto
-- - removed ace (defined in TELESTE-ROOT-MIB) and ace8 (defined in TELESTE-ACE-MIB).
-- - removed acxOpticalReceiverAlarmLimitSet and acxOpticalReceiverAlarmLimitDistance (defined in TELESTE-FUNCTIONAL-OPTICAL-FORWARD-RECEIVER-MIB).
-- - removed acxLevelControlButtonSetup, acxLevelControlButtonAcVoltage, acxLevelControlButtonAlscGain, acxLevelControlButtonAlscSlope (defined in TELESTE-FUNCTIONAL-TRANSPONDER-SET-BUTTON-MIB).
-- 
-- 57, 28.2.2014, Sami Kuusisto
-- - added ACE8 (579.8) sysOID.
-- 
-- 56, 25.2.2014, Sami Kuusisto
-- - added AC1000T3 (1003) and AC2000T2 (2003) sysOIDs.
-- 
-- 55, 11.2.2014, Sami Kuusisto
-- - added new enumeration alignCanceled(17) to acxLevelControlAlignmentStatus.
-- 
-- 55, 11.2.2014, Sami Kuusisto
-- - added new enumeration alignWaitingForRun(16) to acxLevelControlAlignmentStatus.
-- 
-- 54, 24.1.2014, Sami Kuusisto
-- - fixed acxOpticalReceiverAlarmLimitSet type.
-- 
-- 53, 23.1.2014, Sami Kuusisto
-- - added acxOpticalReceiverAlarmLimitSet and acxOpticalReceiverAlarmLimitDistance.
-- - removed acxLevelControlButtonOpticalReceiver and renumbered acxLevelControlButtonAcVoltage/AlscGain/AlscSlope.
-- 
-- 52, 14.1.2014, Sami Kuusisto
-- - added new states 4-7 to acxAlscTargetLevelUse.
-- 
-- 52, 14.1.2014, Sami Kuusisto
-- - added new states (alignReserved(6) and alignAll(7) to acxLevelControlStartAlignment.
-- 
-- 51, 8.1.2014, Sami Kuusisto
-- - added acxLevelControlButtonAlscGain and acxLevelControlButtonAlscSlope.
-- 
-- 50, 22.11.2013, Sami Kuusisto
-- - added acxLevelControlButtonSetup, acxLevelControlButtonOpticalReceiver, acxLevelControlButtonAcVoltage
-- 
-- 49, 9.10.2013, Sami Kuusisto
-- - added 1.2 GHz enum to acxForwardPathBand
-- 
-- 48, 9.9.2013, Sami Halen
-- - added rf1rf2tx1andrf3rf4tx2 to acxReturnPathRoutingControl/acxReturnPathRoutingStatus
-- 
-- 47, 20.8.2013, Sami Kuusisto
-- - added AC3200 (606) 3rd gen OID.
-- 
-- 46, 26.6.2013, Sami Kuusisto
-- - added Description to acxLevelControlGainStatus and acxLevelControlGainStatus.
-- - added saturatedAtMinimum(6) and saturatedAtMaximum(7) to acxAlscGainStatus/acxAlscSlopeStatus.
-- 
-- 45, 26.6.2013, Sami Kuusisto
-- - added acxLevelControlGainStatus and acxLevelControlGainStatus.
-- 
-- 44, 16.1.2013, Sami Halen
-- - added ac3000-1stgen, ac3000-2ndgen, ac3200-1stgen, ac3200-2ndgen,
--   ac3000-1stgen-606, ac3000-2ndgen-606, ac3200-1stgen-606, ac3200-2ndgen-606 sysOIDs
-- - renamed ac9000plus sysOID to ac9000-2ndgen
-- - removed ac9000i sysOID
-- 
-- 43, 29.11.2012, Sami Halen
-- - editorial: acxReturnPathModemRouting text changed
-- 
-- 42, 13.11.2012, Sami Halen
-- - added acxReturnPathNumberOfInputs
-- - added acxReturnPathInputTable
-- 
-- 41, 29.8.2012, Sami Halen
-- - updated acxReturnTransmitterPilotFrequency texts
-- - added ac9000plus and ac9000i sysOIDs
-- - editorial: changed all "optional" statuses to "mandatory"
-- - editorial: added "acx" prefix to ingressSwitch control mode & delay OIDs
-- 
-- 40, 1.6.2012, Sami Halen
-- - added acxReturnPathModemRouting
-- - added powerSaveLaser(3) to acxReturnPathPowerSave
-- - added offRfAndLaser(3) to returnTransmitterMode
-- - editorial: added "acx" prefix to acxOpticalReceiverTable OIDs
-- - editorial: added "acx" prefix toacxReturnTransmitterTable OIDs
-- - editorial: changed acxForwardPathOmiAlign table OID names to match table name
-- - editorial: changed acxReturnPathOmiAlignTable table OID names to match table name
-- 
-- 39, 19.3.2012, Sami Halen
-- - added returnTransmitterRfLevel1Status and returnTransmitterRfLevel2Status
-- - updated opticalReceiverInputPowerStatus, returnTransmitterLaserStatus, 
--   and acxLevelDetectorStatus to use ValueStatus from TELESTE-ROOT-MIB
-- - some cleanup
-- 
-- 38, 15.2.2012, Sami Halen
-- - added enumerations to acxModuleStatus and acxTransponderStatus
-- 
-- 37, 30.1.2012, Sami Halen
-- - added ac8700
-- 
-- 36, 17.1.2012, Sami Halen
-- - added returnTransmitterRfLevel1/2
-- 
-- 1.35, 14.12.2011, Sami Halen
-- - added TDA802&TDA804 to acxForwardPathCableSimulator, renamed to acxForwardPathPluginType
-- 
-- 1.34, 13.9.2011, Sami Halen
-- - added objects for AC9000
-- 
-- 1.33, 6.5.2011, Sami Halen
-- - added acxForwardPathPluginControl
-- 
-- 1.32, 28.9.2010, Sami Salo
-- - added opticalReceiverReferenceLevel to acxOpticalReceiverTable
-- 
-- 1.31, 29.4.2010, Matti Susi
-- - added TXE602 to acxForwardPathCableSimulator selections
-- 
-- 1.30, 24.6.2009, Matti Susi
-- - regenerated builder file from version 1.29
-- - minor editorial changes
-- 
-- 1.29,11.6.2009, Sami Kuusisto
-- - Corrected acxFwdOmiAlignTransmitterOmi unit to %.
-- 
-- 1.28,11.6.2009, Sami Kuusisto & Rainer Salminen
-- - edited acxForwardPathOmiAlignTable and acxReturnPathOmiAlignTable (for AC8800)
-- 
-- 1.27,5.4.2009, Matti Susi
-- - added objects for AC8800
-- 
-- 1.26, 23.3.2009, Matti Susi
-- - added objects for 606 MHz models
-- 
-- 1.25, 10.2.2009, Matti Susi
-- - added AC800i and AC800Z sysOIDs
-- 
-- 1.24, 28.4.2008, Matti Susi
-- - extended acxLevelControlAlignmentStatus enumeration
-- - corrected acxAlscTargetLevelBackoff value range
-- 
-- 1.23, 26.3.2008, Matti Susi
-- - added some additional AC3x00 specific objects
-- 
-- 1.22, 6.2.2008, Matti Susi
-- - added objects acxModuleStatus, acxAlscControlStatus, acxTransponderStatus
-- - renamed 'Controller' to 'Transponder'
-- 
-- 1.21, 22.1.2008, Matti Susi
-- - added some enumerations to support not implemented parameters
-- - removed object acxSystemSlope
-- - added pilot backoff object acxAlscTargetLevelBackoff
-- 
-- 1.2, 2.10.2007, Matti Susi
-- - added multiple new objects to support AC6951 and AC3000 series devices
-- - changed some existing object names
-- - changed and extended some enumerations
-- 
-- 1.1, 4.11.2004, Matti Susi
-- - added new spectrum analyser objects
-- 
-- 1.0, 1.9.2004, Matti Susi
-- - First official release
-- 
-- ****************************************************************************
-- 

	TELESTE-ACX-MIB DEFINITIONS ::= BEGIN
 
		IMPORTS
			OBJECT-TYPE			
				FROM RFC-1212			
			TRAP-TYPE			
				FROM RFC-1215			
			moduleId			
				FROM TELESTE-COMMON-MIB			
			acx, ValueStatus			
				FROM TELESTE-ROOT-MIB;
	
	
	
--
-- Node definitions
--
	
		-- 1.3.6.1.4.1.3715.11.1
		acxStation OBJECT IDENTIFIER ::= { acx 1 }

		
		-- 1.3.6.1.4.1.3715.11.1.1
		acxNumberOfPowerSupplies OBJECT-TYPE
			SYNTAX INTEGER (1..8)
			ACCESS read-only
			STATUS mandatory
			DESCRIPTION
				"The number of power supplies available in the device."
			::= { acxStation 1 }

		
		-- 1.3.6.1.4.1.3715.11.1.2
		acxSupplyVoltageRMS OBJECT-TYPE
			SYNTAX INTEGER
			ACCESS read-only
			STATUS mandatory
			DESCRIPTION
				"RMS value of the remote supply voltage. Unit 0.01 V.
				This object has an entry in the propertyTable."
			::= { acxStation 2 }

		
		-- 1.3.6.1.4.1.3715.11.1.3
		acxSupplyVoltageAC OBJECT-TYPE
			SYNTAX INTEGER
			ACCESS read-only
			STATUS mandatory
			DESCRIPTION
				"AC value of the remote supply voltage. Unit 0.01 V."
			::= { acxStation 3 }

		
		-- 1.3.6.1.4.1.3715.11.1.4
		acxSupplyVoltageDC OBJECT-TYPE
			SYNTAX INTEGER
			ACCESS read-only
			STATUS mandatory
			DESCRIPTION
				"DC value of the remote supply voltage. Unit 0.01 V."
			::= { acxStation 4 }

		
		-- 1.3.6.1.4.1.3715.11.1.5
		acx24VPsu1 OBJECT-TYPE
			SYNTAX INTEGER
			ACCESS read-only
			STATUS mandatory
			DESCRIPTION
				"+24 VDC voltage from power supply 1. Unit 0.01 V.
				This object has an entry in the propertyTable."
			::= { acxStation 5 }

		
		-- 1.3.6.1.4.1.3715.11.1.6
		acx24VPsu2 OBJECT-TYPE
			SYNTAX INTEGER
			ACCESS read-only
			STATUS mandatory
			DESCRIPTION
				"+24 VDC voltage from power supply 2. Unit 0.01 V.
				This object has an entry in the propertyTable."
			::= { acxStation 6 }

		
		-- 1.3.6.1.4.1.3715.11.1.7
		acx12VCommon OBJECT-TYPE
			SYNTAX INTEGER
			ACCESS read-only
			STATUS mandatory
			DESCRIPTION
				"The +12 VDC voltage from power supply. Unit 0.01 V.
				This object has an entry in the propertyTable."
			::= { acxStation 7 }

		
		-- 1.3.6.1.4.1.3715.11.1.10
		acxPort3Usage OBJECT-TYPE
			SYNTAX INTEGER
				{
				portInputBypass(1),
				portOutput3(2),
				portNotAvailable(3)
				}
			ACCESS read-only
			STATUS mandatory
			DESCRIPTION
				"RF port 3 usage:
				1 = port 3 used as input bypass output
				2 = port 3 used as third output
				3 = the platform has no port 3 or the
				    information is not available from the hardware"
			::= { acxStation 10 }

		
		-- 1.3.6.1.4.1.3715.11.1.11
		acxModuleStatus OBJECT-TYPE
			SYNTAX INTEGER
				{
				statusNormal(1),
				statusUnknownModule(2),
				statusInternalError(3),
				statusNotPowered(4)
				}
			ACCESS read-only
			STATUS mandatory
			DESCRIPTION
				"Status of modules installed on the ACx motherboard
				1 = all modules are properly identified
				2 = one or more unknown modules are present
				3 = internal error in motherboard
				4 = motherboard partially powered, no full functionality"
			::= { acxStation 11 }

		
		-- 1.3.6.1.4.1.3715.11.1.12
		acxPsu1Status OBJECT-TYPE
			SYNTAX INTEGER
				{
				acxPsu1StatusOk(1),
				acxPsu1StatusFailure(2),
				acxPsu1StatusNA(3),
				acxPsu1StatusConnectionLost(4)
				}
			ACCESS read-only
			STATUS mandatory
			DESCRIPTION
				"Power supply 1 status.
				1: OK
				2: Failure
				3: Power supply 1 status not available.
				4: Connection lost."
			::= { acxStation 12 }

		
		-- 1.3.6.1.4.1.3715.11.1.13
		acxPsu2Status OBJECT-TYPE
			SYNTAX INTEGER
				{
				acxPsu2StatusOk(1),
				acxPsu2StatusFailure(2),
				acxPsu2StatusNA(3),
				acxPsu2StatusConnectionLost(4)
				}
			ACCESS read-only
			STATUS mandatory
			DESCRIPTION
				"Power supply 2 status.
				1: OK
				2: Failure
				3: Power supply 2 status not available.
				4: Connection lost."
			::= { acxStation 13 }

		
		-- 1.3.6.1.4.1.3715.11.1.14
		acxPsu1Type OBJECT-TYPE
			SYNTAX INTEGER
				{
				acxPsu1TypeICON6300_OK(2),
				acxPsu1TypeICON6300_FAIL(4),
				acxPsu1TypeNoPSU(8),
				acxPsu1TypeNA(15),
				acxPsu1TypeLuminatoPSU(16)
				}
			ACCESS read-only
			STATUS mandatory
			DESCRIPTION
				"Detected power supply 1 type.
				2: ICON6300 PSU: Status OK
				4: ICON6300 PSU: One or more voltages failed.
				8: No PSU at this slot present.
				15: Device doesn't support automatic power supply type detection.
				16: Luminato PSU"
			::= { acxStation 14 }

		
		-- 1.3.6.1.4.1.3715.11.1.15
		acxPsu2Type OBJECT-TYPE
			SYNTAX INTEGER
				{
				acxPsu2TypeICON6300_OK(2),
				acxPsu2TypeICON6300_FAIL(4),
				acxPsu2TypeNoPSU(8),
				acxPsu2TypeNA(15),
				acxPsu2TypeLuminatoPSU(16)
				}
			ACCESS read-only
			STATUS mandatory
			DESCRIPTION
				"Detected power supply 2 type.
				2: ICON6300 PSU: Status OK
				4: ICON6300 PSU: One or more voltages failed.
				8: No PSU at this slot present.
				15: Device doesn't support automatic power supply type detection.
				16: Luminato PSU"
			::= { acxStation 15 }

		
		-- 1.3.6.1.4.1.3715.11.1.16
		acxSupplyVoltageRMS2 OBJECT-TYPE
			SYNTAX INTEGER
			ACCESS read-only
			STATUS mandatory
			DESCRIPTION
				"RMS value of the remote supply 2 voltage. Unit 0.01 V.
				This object has an entry in the propertyTable, if remote supply 2 is present. If remote supply 2 is not present, value is 0 V."
			::= { acxStation 16 }

		
		-- 1.3.6.1.4.1.3715.11.1.17
		acx34VPsu1 OBJECT-TYPE
			SYNTAX INTEGER
			ACCESS read-only
			STATUS mandatory
			DESCRIPTION
				"+34 VDC voltage from power supply 1. Unit 0.01 V.
				This object has an entry in the propertyTable."
			::= { acxStation 17 }

		
		-- 1.3.6.1.4.1.3715.11.1.18
		acx34VPsu2 OBJECT-TYPE
			SYNTAX INTEGER
			ACCESS read-only
			STATUS mandatory
			DESCRIPTION
				"+34 VDC voltage from power supply 2. Unit 0.01 V.
				This object has an entry in the propertyTable."
			::= { acxStation 18 }

		
		-- 1.3.6.1.4.1.3715.11.1.19
		acxSupplyVoltageCrestFactor OBJECT-TYPE
			SYNTAX INTEGER
			ACCESS read-only
			STATUS mandatory
			DESCRIPTION
				"Crest factor of the remote supply voltage. Unit 0.01."
			::= { acxStation 19 }

		
		-- 1.3.6.1.4.1.3715.11.1.20
		acxSupplyVoltagePeakValue OBJECT-TYPE
			SYNTAX INTEGER
			ACCESS read-only
			STATUS mandatory
			DESCRIPTION
				"Peak value of the remote supply voltage. Unit 0.01 V."
			::= { acxStation 20 }

		
		-- 1.3.6.1.4.1.3715.11.1.21
		acx12VPsu2 OBJECT-TYPE
			SYNTAX INTEGER
			ACCESS read-only
			STATUS mandatory
			DESCRIPTION
				"The +12 VDC voltage from power supply 2. Unit 0.01 V.
				This object has an entry in the propertyTable."
			::= { acxStation 21 }

		
		-- 1.3.6.1.4.1.3715.11.4
		acxForwardPath OBJECT IDENTIFIER ::= { acx 4 }

		
		-- 1.3.6.1.4.1.3715.11.4.1
		acxNumberOfOpticalReceivers OBJECT-TYPE
			SYNTAX INTEGER (0..8)
			ACCESS read-only
			STATUS mandatory
			DESCRIPTION
				"The number of optical receivers available in the device."
			::= { acxForwardPath 1 }

		
		-- 1.3.6.1.4.1.3715.11.4.2
		acxOpticalInputSelectionMode OBJECT-TYPE
			SYNTAX INTEGER
				{
				manual1(1),
				manual2(2),
				autoRevertive(3),
				autoNonRevertive(4),
				noBackup(5)
				}
			ACCESS read-write
			STATUS mandatory
			DESCRIPTION
				"Input selection mode:
				1 = manual, input 1
				2 = manual, input 2
				3 = automatic, revertive
				4 = automatic, non-revertive
				5 = no backup"
			::= { acxForwardPath 2 }

		
		-- 1.3.6.1.4.1.3715.11.4.3
		acxActiveOpticalInput OBJECT-TYPE
			SYNTAX INTEGER
				{
				input1(1),
				input2(2),
				input1and2(3),
				inputNA(4)
				}
			ACCESS read-only
			STATUS mandatory
			DESCRIPTION
				"Active optical input status:
				1 = input 1
				2 = input 2
				3 = input 1 and input 2
				4 = N/A"
			::= { acxForwardPath 3 }

		
		-- 1.3.6.1.4.1.3715.11.4.4
		acxOpticalReceiverTable OBJECT-TYPE
			SYNTAX SEQUENCE OF AcxOpticalReceiverEntry
			ACCESS not-accessible
			STATUS mandatory
			DESCRIPTION
				"A table of optical receiver control entries."
			::= { acxForwardPath 4 }

		
		-- 1.3.6.1.4.1.3715.11.4.4.1
		acxOpticalReceiverEntry OBJECT-TYPE
			SYNTAX AcxOpticalReceiverEntry
			ACCESS not-accessible
			STATUS mandatory
			INDEX { moduleId }
			::= { acxOpticalReceiverTable 1 }

		
		AcxOpticalReceiverEntry ::=
			SEQUENCE { 
				acxOpticalReceiverInputPower
					INTEGER,
				acxOpticalReceiverMode
					INTEGER,
				acxOpticalReceiverInputPowerStatus
					ValueStatus,
				acxOpticalReceiverEnable
					INTEGER,
				acxOpticalReceiverReferenceLevel
					INTEGER,
				acxOpticalReceiverOlcOffset
					INTEGER,
				acxOpticalReceiverAnalogOffset
					INTEGER,
				acxOpticalReceiverAnalogOffsetMin
					INTEGER,
				acxOpticalReceiverAnalogOffsetMax
					INTEGER,
				acxOpticalReceiverAnalogOffsetStepSize
					INTEGER,
				acxOpticalReceiverOpticalPowerMinLevel
					INTEGER,
				acxOpticalReceiverOpticalPowerMaxLevel
					INTEGER
			 }

		-- 1.3.6.1.4.1.3715.11.4.4.1.1
		acxOpticalReceiverInputPower OBJECT-TYPE
			SYNTAX INTEGER
			ACCESS read-only
			STATUS mandatory
			DESCRIPTION
				"Optical input power value. Unit 0.01 dBm.
				This object has an entry in the propertyTable."
			::= { acxOpticalReceiverEntry 1 }

		
		-- 1.3.6.1.4.1.3715.11.4.4.1.2
		acxOpticalReceiverMode OBJECT-TYPE
			SYNTAX INTEGER
				{
				on(1),
				off(2)
				}
			ACCESS read-write
			STATUS mandatory
			DESCRIPTION
				"Optical receiver module operating mode:
				1 = receiver ON
				2 = receiver OFF
				
				In devices with only one integrated optical receiver, like AC800,
				this object controls the optical level based ALC ('OLC'):
				on(1) = OLC ON - automatic level control
				off(2) = OLC OFF - manual level control"
			::= { acxOpticalReceiverEntry 2 }

		
		-- 1.3.6.1.4.1.3715.11.4.4.1.3
		acxOpticalReceiverInputPowerStatus OBJECT-TYPE
			SYNTAX ValueStatus
			ACCESS read-only
			STATUS mandatory
			DESCRIPTION
				"Optical input power status:
				1 = normal
				2 = HIHI
				3 = HI
				4 = LO
				5 = LOLO"
			::= { acxOpticalReceiverEntry 3 }

		
		-- 1.3.6.1.4.1.3715.11.4.4.1.4
		acxOpticalReceiverEnable OBJECT-TYPE
			SYNTAX INTEGER
				{
				rxEnabled(1),
				rxDisabled(2)
				}
			ACCESS read-write
			STATUS mandatory
			DESCRIPTION
				"Optical receiver enabling:
				1 = receiver is enabled
				2 = receiver is disabled"
			::= { acxOpticalReceiverEntry 4 }

		
		-- 1.3.6.1.4.1.3715.11.4.4.1.5
		acxOpticalReceiverReferenceLevel OBJECT-TYPE
			SYNTAX INTEGER
			ACCESS read-write
			STATUS mandatory
			DESCRIPTION
				"Optical receiver reference level. Unit 0.01 dBm."
			::= { acxOpticalReceiverEntry 5 }

		
		-- 1.3.6.1.4.1.3715.11.4.4.1.6
		acxOpticalReceiverOlcOffset OBJECT-TYPE
			SYNTAX INTEGER
			ACCESS read-write
			STATUS mandatory
			DESCRIPTION
				"OLC (Optical Level Control) offset. Unit 0.01 dB."
			::= { acxOpticalReceiverEntry 6 }

		
		-- 1.3.6.1.4.1.3715.11.4.4.1.7
		acxOpticalReceiverAnalogOffset OBJECT-TYPE
			SYNTAX INTEGER
			ACCESS read-write
			STATUS mandatory
			DESCRIPTION
				"Analog offset. Unit 0.01 dB."
			::= { acxOpticalReceiverEntry 7 }

		
		-- 1.3.6.1.4.1.3715.11.4.4.1.8
		acxOpticalReceiverAnalogOffsetMin OBJECT-TYPE
			SYNTAX INTEGER
			ACCESS read-only
			STATUS mandatory
			DESCRIPTION
				"Analog offset minimum value. Unit 0.01 dB."
			::= { acxOpticalReceiverEntry 8 }

		
		-- 1.3.6.1.4.1.3715.11.4.4.1.9
		acxOpticalReceiverAnalogOffsetMax OBJECT-TYPE
			SYNTAX INTEGER
			ACCESS read-only
			STATUS mandatory
			DESCRIPTION
				"Analog offset maximum value. Unit 0.01 dB."
			::= { acxOpticalReceiverEntry 9 }

		
		-- 1.3.6.1.4.1.3715.11.4.4.1.10
		acxOpticalReceiverAnalogOffsetStepSize OBJECT-TYPE
			SYNTAX INTEGER
			ACCESS read-only
			STATUS mandatory
			DESCRIPTION
				"Analog offset step size. Unit 0.01 dB."
			::= { acxOpticalReceiverEntry 10 }

		
		-- 1.3.6.1.4.1.3715.11.4.4.1.11
		acxOpticalReceiverOpticalPowerMinLevel OBJECT-TYPE
			SYNTAX INTEGER
			ACCESS read-only
			STATUS mandatory
			DESCRIPTION
				"Minimum optical level (0.01 dBm) when OLC works."
			::= { acxOpticalReceiverEntry 11 }

		
		-- 1.3.6.1.4.1.3715.11.4.4.1.12
		acxOpticalReceiverOpticalPowerMaxLevel OBJECT-TYPE
			SYNTAX INTEGER
			ACCESS read-only
			STATUS mandatory
			DESCRIPTION
				"Maximum optical level (0.01 dBm) when OLC works."
			::= { acxOpticalReceiverEntry 12 }

		
		-- 1.3.6.1.4.1.3715.11.4.5
		acxForwardPathBand OBJECT-TYPE
			SYNTAX INTEGER
				{
				band862MHz(1),
				band1GHz(2),
				bandNotAvailable(3),
				band606MHz(4),
				band1218MHz(5),
				bandOther(6)
				}
			ACCESS read-write
			STATUS mandatory
			DESCRIPTION
				"Forward path frequency range:
				1 = band862MHz - 862 MHz forward path
				2 = band1GHz - 1 GHz forward path
				3 = bandNotAvailable - adjustable forward path band not supported
				4 = band606MHz - 606 MHz forward path
				5 = band1218MHz - 1.2 GHz forward path
				6 = bandOther - other forward path band"
			::= { acxForwardPath 5 }

		
		-- 1.3.6.1.4.1.3715.11.4.6
		acxForwardPathPluginStatus OBJECT-TYPE
			SYNTAX INTEGER
				{
				plugNotInstalled(1),
				plugInUse(2),
				plugNotInUse(3)
				}
			ACCESS read-only
			STATUS mandatory
			DESCRIPTION
				"Type of the forward path plug-in module:
				1 = plug not installed
				2 = plug in use
				3 = plug not in use (bypassed)
				
				If the platform has no plug-in slot, value plugNotInstalled(1) is returned."
			::= { acxForwardPath 6 }

		
		-- 1.3.6.1.4.1.3715.11.4.7
		acxForwardPathPluginType OBJECT-TYPE
			SYNTAX INTEGER
				{
				pluginNone(1),
				pluginOther(2),
				pluginTXS802(3),
				pluginTXS804(4),
				pluginTXS808(5),
				pluginTXE605(6),
				pluginTXE602(7),
				pluginTDA802(8),
				pluginTDA804(9)
				}
			ACCESS read-write
			STATUS mandatory
			DESCRIPTION
				"Plug-in module type installed into the universal plug-in slot:
				1 = no cable simulator
				2 = other/unknown cable simulator type
				3 = TXS802 cable simulator
				4 = TXS804 cable simulator
				5 = TXS808 cable simulator
				6 = TXE605 equaliser
				7 = TXE602 equaliser
				8 = TDA802 attenuator
				9 = TDA804 attenuator"
			::= { acxForwardPath 7 }

		
		-- 1.3.6.1.4.1.3715.11.4.8
		acxForwardPathOlcOffset OBJECT-TYPE
			SYNTAX INTEGER
			ACCESS read-write
			STATUS mandatory
			DESCRIPTION
				"OLC (Optical Level Control) offset. Unit 0.01 dB."
			::= { acxForwardPath 8 }

		
		-- 1.3.6.1.4.1.3715.11.4.9
		acxNumberOfForwardPathOmiEntries OBJECT-TYPE
			SYNTAX INTEGER (0..8)
			ACCESS read-only
			STATUS mandatory
			DESCRIPTION
				"The number of entries in the acxForwardPathOmiAlignTable"
			::= { acxForwardPath 9 }

		
		-- 1.3.6.1.4.1.3715.11.4.10
		acxForwardPathOmiAlignTable OBJECT-TYPE
			SYNTAX SEQUENCE OF AcxForwardPathOmiAlignEntry
			ACCESS not-accessible
			STATUS mandatory
			DESCRIPTION
				"A table of forward path OMI based alignment entries."
			::= { acxForwardPath 10 }

		
		-- 1.3.6.1.4.1.3715.11.4.10.1
		acxForwardPathOmiAlignEntry OBJECT-TYPE
			SYNTAX AcxForwardPathOmiAlignEntry
			ACCESS not-accessible
			STATUS mandatory
			INDEX { acxForwardPathOmiAlignIndex }
			::= { acxForwardPathOmiAlignTable 1 }

		
		AcxForwardPathOmiAlignEntry ::=
			SEQUENCE { 
				acxForwardPathOmiAlignIndex
					INTEGER,
				acxForwardPathOmiAlignTransmitterOmi
					INTEGER,
				acxForwardPathOmiAlignOutputTargetLevel
					INTEGER
			 }

		-- 1.3.6.1.4.1.3715.11.4.10.1.1
		acxForwardPathOmiAlignIndex OBJECT-TYPE
			SYNTAX INTEGER (1..10)
			ACCESS read-only
			STATUS mandatory
			DESCRIPTION
				"The table index. Please note that this index differs from the
				acxOpticalReceiverTable index, which is the module slot number.
				This index refers to the optical receiver 'order number' the settings
				concern, e.g. index value 1 means receiver 1 etc. "
			::= { acxForwardPathOmiAlignEntry 1 }

		
		-- 1.3.6.1.4.1.3715.11.4.10.1.2
		acxForwardPathOmiAlignTransmitterOmi OBJECT-TYPE
			SYNTAX INTEGER
			ACCESS read-write
			STATUS mandatory
			DESCRIPTION
				"Transmitter OMI used for OMI based level control. When the transmitter
				has this OMI, output RF level is set to value opticalReceiverOutputTargetLevel.
				Unit 0.01 %."
			::= { acxForwardPathOmiAlignEntry 2 }

		
		-- 1.3.6.1.4.1.3715.11.4.10.1.3
		acxForwardPathOmiAlignOutputTargetLevel OBJECT-TYPE
			SYNTAX INTEGER
			ACCESS read-write
			STATUS mandatory
			DESCRIPTION
				"Target output level for OMI based level control. When the transmitter
				uses the OMI given by opticalReceiverTransmitterOmi, the output RF level
				is set to this value. Unit 0.01 dBuV."
			::= { acxForwardPathOmiAlignEntry 3 }

		
		-- 1.3.6.1.4.1.3715.11.4.11
		acxForwardPathPluginControl OBJECT-TYPE
			SYNTAX INTEGER
				{
				plugUseIfInstalled(1),
				plugNeverUse(2)
				}
			ACCESS read-write
			STATUS mandatory
			DESCRIPTION
				"Forward path plug-in module usage:
				1 = use the forward path plug-in if it is installed
				2 = never use the forward path plug-in module
				
				If the platform has no plug-in slot, value plugNeverUse(2) is returned."
			::= { acxForwardPath 11 }

		
		-- 1.3.6.1.4.1.3715.11.4.12
		acxOpticalInputControl OBJECT-TYPE
			SYNTAX INTEGER
				{
				input1(1),
				input2(2),
				input1and2(3),
				inputNA(4)
				}
			ACCESS read-write
			STATUS mandatory
			DESCRIPTION
				"Active optical input control:
				1 = input 1
				2 = input 2
				3 = input 1 and input 2
				4 = N/A"
			::= { acxForwardPath 12 }

		
		-- 1.3.6.1.4.1.3715.11.4.13
		acxForwardPathOutputEnable OBJECT-TYPE
			SYNTAX INTEGER
			ACCESS read-write
			STATUS mandatory
			DESCRIPTION
				"Forward path output control.
				Bitmask. Bit set = output enabled.
				Bit 1 = Output 2
				Bit 2 = Output 3
				Bit 3 = Output 4"
			::= { acxForwardPath 13 }

		
		-- 1.3.6.1.4.1.3715.11.4.14
		acxRfPerformance OBJECT-TYPE
			SYNTAX INTEGER
				{
				automatic(1),
				high(2),
				standard(3),
				powersave(4)
				}
			ACCESS read-write
			STATUS mandatory
			DESCRIPTION
				"RF performance adjustment:
				1 = automatic
				2 = high
				3 = standard
				4 = powersave"
			::= { acxForwardPath 14 }

		
		-- 1.3.6.1.4.1.3715.11.4.15
		acxBackupStatus OBJECT-TYPE
			SYNTAX INTEGER
				{
				backupStatusNoBackUp(1),
				backupStatusBackUpActive(2)
				}
			ACCESS read-only
			STATUS mandatory
			DESCRIPTION
				"Backup status
				1: Backup not active.
				2: Backup active."
			::= { acxForwardPath 15 }

		
		-- 1.3.6.1.4.1.3715.11.5
		acxLevelControl OBJECT IDENTIFIER ::= { acx 5 }

		
		-- 1.3.6.1.4.1.3715.11.5.1
		acxNumberOfLevelControlModules OBJECT-TYPE
			SYNTAX INTEGER (0..8)
			ACCESS read-only
			STATUS mandatory
			DESCRIPTION
				"The number of level control modules available in this 
				device. Zero value means that no level control modules 
				are installed."
			::= { acxLevelControl 1 }

		
		-- 1.3.6.1.4.1.3715.11.5.2
		acxLevelControlTable OBJECT-TYPE
			SYNTAX SEQUENCE OF AcxLevelControlEntry
			ACCESS not-accessible
			STATUS mandatory
			DESCRIPTION
				"A table of gain and slope control entries.
				Integrated gain and slope controls are handled as modules, 
				e.g. they must have module table entries."
			::= { acxLevelControl 2 }

		
		-- 1.3.6.1.4.1.3715.11.5.2.1
		acxLevelControlEntry OBJECT-TYPE
			SYNTAX AcxLevelControlEntry
			ACCESS not-accessible
			STATUS mandatory
			INDEX { moduleId }
			::= { acxLevelControlTable 1 }

		
		AcxLevelControlEntry ::=
			SEQUENCE { 
				acxLevelControlGain
					INTEGER,
				acxLevelControlSlope
					INTEGER,
				acxLevelControlType
					INTEGER,
				acxLevelControlGainStatus
					INTEGER,
				acxLevelControlSlopeStatus
					INTEGER
			 }

		-- 1.3.6.1.4.1.3715.11.5.2.1.1
		acxLevelControlGain OBJECT-TYPE
			SYNTAX INTEGER
			ACCESS read-write
			STATUS mandatory
			DESCRIPTION
				"Gain control value Unit 0.01 dB. The gain value may be read-only
				when ALSC is switched on.
				
				If the control does not include gain, gain value 0 is returned."
			::= { acxLevelControlEntry 1 }

		
		-- 1.3.6.1.4.1.3715.11.5.2.1.2
		acxLevelControlSlope OBJECT-TYPE
			SYNTAX INTEGER
			ACCESS read-write
			STATUS mandatory
			DESCRIPTION
				"Slope control value. Unit 0.01 dB. The slope value may be read-only
				when ALSC is switched on.
				
				If the control does not include slope, slope value 0 is returned."
			::= { acxLevelControlEntry 2 }

		
		-- 1.3.6.1.4.1.3715.11.5.2.1.3
		acxLevelControlType OBJECT-TYPE
			SYNTAX INTEGER
				{
				controlInput(1),
				controlInterstage(2),
				controlTotal(3),
				controlReturnPath(4),
				controlOther(5),
				controlOutput(6)
				}
			ACCESS read-only
			STATUS mandatory
			DESCRIPTION
				"Type of the control module entry:
				1 = controlInput - input gain and slope control
				2 = controlInterstage - interstage gain and slope control
				3 = controlTotal - total gain (and slope) control
				4 = controlReturnpath - return path gain and slope control
				5 = controlOther - other gain and slope control
				6 = controlOutput - output gain and slope control"
			::= { acxLevelControlEntry 3 }

		
		-- 1.3.6.1.4.1.3715.11.5.2.1.4
		acxLevelControlGainStatus OBJECT-TYPE
			SYNTAX INTEGER
				{
				normal(1),
				minimum(2),
				maximum(3),
				frozen(4),
				default(5),
				saturatedAtMinimum(6),
				saturatedAtMaximum(7)
				}
			ACCESS read-only
			STATUS mandatory
			DESCRIPTION
				"Gain control status:
				1 = normal
				2 = minimum (control at minimum, but no request to adjust under minimum)
				3 = maximum (control at maximum, but no request to adjust over maximum)
				4 = frozen (not used)
				5 = default (not used)
				6 = saturatedAtMinimum (control saturated at minimum value, but there's need to adjust under minimum)
				7 = saturatedAtMaximum (control saturated at maximum value, but there's need to adjust over maximum)
								
				Returns value normal(1) when gain control not available."
			::= { acxLevelControlEntry 4 }

		
		-- 1.3.6.1.4.1.3715.11.5.2.1.5
		acxLevelControlSlopeStatus OBJECT-TYPE
			SYNTAX INTEGER
				{
				normal(1),
				minimum(2),
				maximum(3),
				frozen(4),
				default(5),
				saturatedAtMinimum(6),
				saturatedAtMaximum(7)
				}
			ACCESS read-only
			STATUS mandatory
			DESCRIPTION
				"Slope control status:
				1 = normal
				2 = minimum (control at minimum, but no request to adjust under minimum)
				3 = maximum (control at maximum, but no request to adjust over maximum)
				4 = frozen (not used)
				5 = default (not used)
				6 = saturatedAtMinimum (control saturated at minimum value, but there's need to adjust under minimum)
				7 = saturatedAtMaximum (control saturated at maximum value, but there's need to adjust over maximum)
								
				Returns value normal(1) when slope control not available."
			::= { acxLevelControlEntry 5 }

		
		-- 1.3.6.1.4.1.3715.11.5.5
		acxLevelControlStartAlignment OBJECT-TYPE
			SYNTAX INTEGER
				{
				alignForward(1),
				alignReturn(2),
				alignBoth(3),
				alignNotAvailable(4),
				alignForwardOmiBased(5),
				alignReserved(6),
				alignAll(7)
				}
			ACCESS read-write
			STATUS mandatory
			DESCRIPTION
				"This object is used to start the intelligent gain alignment prodecure:
				1 = writing this value starts the forward path alignment procedure
				2 = writing this value starts the return path alignment procedure
				3 = writing this value starts the alignment procedure for both paths (same as running first 1 and then 2).
				4 = the device does not support intelligent alignment
				5 = writing this value starts the forward path alignment procedure based on optical OMI
				6 = reserved for future purposes
				7 = writing this value starts all the alignment procedures.
				When reading, this object always returns value alignNotAvailable(4)."
			::= { acxLevelControl 5 }

		
		-- 1.3.6.1.4.1.3715.11.5.6
		acxLevelControlAlignmentStatus OBJECT-TYPE
			SYNTAX INTEGER
				{
				alignNeverRun(1),
				alignRunning(2),
				alignSuccess(3),
				alignNoTunerModule(4),
				alignTargetsOutOfRange(5),
				alignInterStageSlopeOutOfRange(6),
				alignPilotsNotFound(7),
				alignInputSlopeOutOfRange(8),
				alignGainTargetOutOfRange(9),
				alignCableSimulatorNeeded(10),
				alignGainOrSlopeSaturated(11),
				alignUnknownForwardPathPlug(12),
				alignGain2TargetOutOfRange(13),
				alignInterStage2SlopeOutOfRange(14),
				alignOpticalInputPowerOutOfRange(15),
				alignWaitingForRun(16),
				alignCanceled(17)
				}
			ACCESS read-only
			STATUS mandatory
			DESCRIPTION
				"Status of last forward path automatic aligment:
				1 = never run
				2 = running
				3 = success
				4 = no tuner module
				5 = targets out of range
				6 = interstage slope target ouf of range
				7 = pilots not found
				8 = input slope out of range
				9 = gain target out of range
				10 = a cable simulator may be needed into the universal plug-in slot
				11 = gain or slope is saturated
				12 = unknown forward path plug-in module
				13 = alignGain2TargetOutOfRange
				14 = alignInterStage2SlopeOutOfRange
				15 = alignOpticalInputPowerOutOfRange
				16 = alignWaitingForRun
				17 = alignCanceled
				When acxAlscControlMode is set to 'manual' or 'ALSC' this object always returns value alignSuccess(3)."
			::= { acxLevelControl 6 }

		
		-- 1.3.6.1.4.1.3715.11.5.7
		acxLevelControlButtonMode OBJECT-TYPE
			SYNTAX INTEGER
				{
				buttonEnable(1),
				buttonDisable(2),
				buttonNotAvailable(3)
				}
			ACCESS read-write
			STATUS mandatory
			DESCRIPTION
				"Activation/deactivation of the local alignment button:
				1 = pressing the local button start automatic forward path alignment
				2 = pressing the local button has no effect
				3 = the platform has no alignment button"
			::= { acxLevelControl 7 }

		
		-- 1.3.6.1.4.1.3715.11.6
		acxReturnPath OBJECT IDENTIFIER ::= { acx 6 }

		
		-- 1.3.6.1.4.1.3715.11.6.1
		acxNumberOfReturnTransmitters OBJECT-TYPE
			SYNTAX INTEGER (0..8)
			ACCESS read-only
			STATUS mandatory
			DESCRIPTION
				"The number of return transmitters available in the device."
			::= { acxReturnPath 1 }

		
		-- 1.3.6.1.4.1.3715.11.6.2
		acxReturnLaserActivity OBJECT-TYPE
			SYNTAX INTEGER
				{
				laserBothActive(1),
				laserFollowSignalRelay(2),
				laserNotAvailable(3)
				}
			ACCESS read-write
			STATUS mandatory
			DESCRIPTION
				"Optical return transmitter mode:
				1 = both active
				2 = only selected TX is active (follows signal relay position)
				3 = there is no return transmitter installed"
			::= { acxReturnPath 2 }

		
		-- 1.3.6.1.4.1.3715.11.6.3
		acxReturnTransmitterTable OBJECT-TYPE
			SYNTAX SEQUENCE OF AcxReturnTransmitterEntry
			ACCESS not-accessible
			STATUS mandatory
			DESCRIPTION
				"A table of return transmitter control entries."
			::= { acxReturnPath 3 }

		
		-- 1.3.6.1.4.1.3715.11.6.3.1
		acxReturnTransmitterEntry OBJECT-TYPE
			SYNTAX AcxReturnTransmitterEntry
			ACCESS not-accessible
			STATUS mandatory
			INDEX { moduleId }
			::= { acxReturnTransmitterTable 1 }

		
		AcxReturnTransmitterEntry ::=
			SEQUENCE { 
				acxReturnTransmitterLaserBias
					INTEGER,
				acxReturnTransmitterMode
					INTEGER,
				acxReturnTransmitterPilotMode
					INTEGER,
				acxReturnTransmitterLaserStatus
					ValueStatus,
				acxReturnTransmitterPilotFrequency
					INTEGER,
				acxReturnTransmitterBand
					INTEGER,
				acxReturnTransmitterRfLevel1
					INTEGER,
				acxReturnTransmitterRfLevel2
					INTEGER,
				acxReturnTransmitterRfLevel1Status
					ValueStatus,
				acxReturnTransmitterRfLevel2Status
					ValueStatus,
				acxReturnTransmitterItuChannel
					INTEGER,
				acxReturnTransmitterStatus
					INTEGER
			 }

		-- 1.3.6.1.4.1.3715.11.6.3.1.1
		acxReturnTransmitterLaserBias OBJECT-TYPE
			SYNTAX INTEGER
			ACCESS read-only
			STATUS mandatory
			DESCRIPTION
				"Return transmitter laser bias current. Unit 0.01 mA.
				This object has an entry in the propertyTable."
			::= { acxReturnTransmitterEntry 1 }

		
		-- 1.3.6.1.4.1.3715.11.6.3.1.2
		acxReturnTransmitterMode OBJECT-TYPE
			SYNTAX INTEGER
				{
				on(1),
				offRf(2),
				offRfAndLaser(3)
				}
			ACCESS read-write
			STATUS mandatory
			DESCRIPTION
				"Return transmitter operating mode:
				1 = On
				2 = RF stages off
				3 = RF stages and laser off"
			::= { acxReturnTransmitterEntry 2 }

		
		-- 1.3.6.1.4.1.3715.11.6.3.1.3
		acxReturnTransmitterPilotMode OBJECT-TYPE
			SYNTAX INTEGER
				{
				on(1),
				off(2)
				}
			ACCESS read-write
			STATUS mandatory
			DESCRIPTION
				"Return transmitter pilot mode:
				1 = ON
				2 = OFF"
			::= { acxReturnTransmitterEntry 3 }

		
		-- 1.3.6.1.4.1.3715.11.6.3.1.4
		acxReturnTransmitterLaserStatus OBJECT-TYPE
			SYNTAX ValueStatus
			ACCESS read-only
			STATUS mandatory
			DESCRIPTION
				"Return transmitter laser bias current status:
				1 = normal
				2 = HIHI
				3 = HI
				4 = LO
				5 = LOLO"
			::= { acxReturnTransmitterEntry 4 }

		
		-- 1.3.6.1.4.1.3715.11.6.3.1.5
		acxReturnTransmitterPilotFrequency OBJECT-TYPE
			SYNTAX INTEGER
				{
				freqUnknown(1),
				freqOther(2),
				freqLower(3),
				freqUpper(4)
				}
			ACCESS read-write
			STATUS mandatory
			DESCRIPTION
				"Return pilot frequency:
				1 = unknown pilot frequency
				2 = other pilot frequency
				3 = lower (4.5 / 5.5 MHz) pilot frequency
				4 = upper (6.5 MHz) pilot frequency"
			::= { acxReturnTransmitterEntry 5 }

		
		-- 1.3.6.1.4.1.3715.11.6.3.1.6
		acxReturnTransmitterBand OBJECT-TYPE
			SYNTAX INTEGER
				{
				rband30MHz(1),
				rband65MHz(2),
				rband85MHz(3),
				rbandNotAvailable(4),
				rband200MHz(5)
				}
			ACCESS read-write
			STATUS mandatory
			DESCRIPTION
				"Return transmitter frequency range:
				1 = 30/47 MHz return/forward split
				2 = 65/85 MHz return/forward split
				3 = 85/108 MHz return/forward split
				4 = adjustable return path band not supported
				5 = 200 MHz return path band"
			::= { acxReturnTransmitterEntry 6 }

		
		-- 1.3.6.1.4.1.3715.11.6.3.1.7
		acxReturnTransmitterRfLevel1 OBJECT-TYPE
			SYNTAX INTEGER
			ACCESS read-only
			STATUS mandatory
			DESCRIPTION
				"Return transmitter RF input level for channel 1. Unit 0.01 dB."
			::= { acxReturnTransmitterEntry 7 }

		
		-- 1.3.6.1.4.1.3715.11.6.3.1.8
		acxReturnTransmitterRfLevel2 OBJECT-TYPE
			SYNTAX INTEGER
			ACCESS read-only
			STATUS mandatory
			DESCRIPTION
				"Return transmitter RF input level for channel 2. Unit 0.01 dB."
			::= { acxReturnTransmitterEntry 8 }

		
		-- 1.3.6.1.4.1.3715.11.6.3.1.9
		acxReturnTransmitterRfLevel1Status OBJECT-TYPE
			SYNTAX ValueStatus
			ACCESS read-only
			STATUS mandatory
			DESCRIPTION
				"Return transmitter RF input level for channel 1 status:
				1 = normal
				2 = HIHI 
				3 = HI
				4 = LO
				5 = LOLO"
			::= { acxReturnTransmitterEntry 9 }

		
		-- 1.3.6.1.4.1.3715.11.6.3.1.10
		acxReturnTransmitterRfLevel2Status OBJECT-TYPE
			SYNTAX ValueStatus
			ACCESS read-only
			STATUS mandatory
			DESCRIPTION
				"Return transmitter RF input level for channel 2 status:
				1 = normal
				2 = HIHI 
				3 = HI
				4 = LO
				5 = LOLO"
			::= { acxReturnTransmitterEntry 10 }

		
		-- 1.3.6.1.4.1.3715.11.6.3.1.11
		acxReturnTransmitterItuChannel OBJECT-TYPE
			SYNTAX INTEGER
			ACCESS read-only
			STATUS mandatory
			DESCRIPTION
				"ITU channel number."
			::= { acxReturnTransmitterEntry 11 }

		
		-- 1.3.6.1.4.1.3715.11.6.3.1.12
		acxReturnTransmitterStatus OBJECT-TYPE
			SYNTAX INTEGER
				{
				transmitterStatusOk(1),
				transmitterStatusInternalError(2)
				}
			ACCESS read-only
			STATUS mandatory
			DESCRIPTION
				"Transmitter status.
				1: Transmitter ok, no errors
				2: Transmitter has internal error, e.g. laser bias current or TEC current out of limits. If removing and reinstalling the transmitter module doesn't help, contact Teleste support."
			::= { acxReturnTransmitterEntry 12 }

		
		-- 1.3.6.1.4.1.3715.11.6.4
		acxReturnPathBand OBJECT-TYPE
			SYNTAX INTEGER
				{
				rband30MHz(1),
				rband65MHz(2),
				rband85MHz(3),
				rbandNotAvailable(4),
				rband204MHz(5),
				rband42MHz(6),
				rband117MHz(7),
				rbandFDX(8)
				}
			ACCESS read-write
			STATUS mandatory
			DESCRIPTION
				"Return path frequency range:
				1 = 30/47 MHz return/forward split
				2 = 65/85 MHz return/forward split
				3 = 85/108 MHz return/forward split
				4 = adjustable return path band not supported
				5 = 204/258 MHz return path band
				6 = 42/53 MHz return path band
				7 = 117/147 MHz return path band
				8 = Full duplex (FDX)"
			::= { acxReturnPath 4 }

		
		-- 1.3.6.1.4.1.3715.11.6.5
		acxReturnAmplifierType OBJECT-TYPE
			SYNTAX INTEGER
				{
				typeNone(0),
				typeOther(1),
				typeAC6143(2),
				typeAC6144or36(3),
				typeAC6145(4),
				typeAC6147(5)
				}
			ACCESS read-write
			STATUS mandatory
			DESCRIPTION
				"Return amplifier type:
				0 = no amplifier
				1 = other/unknown amplifier type
				2 = AC6143
				3 = AC6144 or AC6136
				4 = AC6145
				5 = AC6147
				The return amplifier type affects the return path spectrum analyser 
				level scaling in AC6951."
			::= { acxReturnPath 5 }

		
		-- 1.3.6.1.4.1.3715.11.6.6
		acxReturnPathPluginStatus OBJECT-TYPE
			SYNTAX INTEGER
				{
				rplugNotInstalled(1),
				rplugInUse(2),
				rplugNotInUse(3)
				}
			ACCESS read-only
			STATUS mandatory
			DESCRIPTION
				"Return path plug-in module status:
				1 = plug not installed
				2 = plug in use
				3 = plug not in use
				
				If the platform has no plug-in slot, value rplugNotInstalled(1) is returned."
			::= { acxReturnPath 6 }

		
		-- 1.3.6.1.4.1.3715.11.6.7
		acxReturnPathPluginControl OBJECT-TYPE
			SYNTAX INTEGER
				{
				plugUseIfInstalled(1),
				plugNeverUse(2),
				plugUseIfIgressAlarm(3)
				}
			ACCESS read-write
			STATUS mandatory
			DESCRIPTION
				"Return path plug-in module usage:
				1 = use the return path plug-in if it is installed
				2 = never use the return path plug-in module
				3 = use the plug-in only when ingress alarm is active
				
				If the platform has no plug-in slot, value plugNeverUse(2) is returned."
			::= { acxReturnPath 7 }

		
		-- 1.3.6.1.4.1.3715.11.6.8
		acxReturnPathAlignmentStatus OBJECT-TYPE
			SYNTAX INTEGER
				{
				alignNeverRun(1),
				alignRunning(2),
				alignSuccess(3),
				alignNoTunerModule(4),
				alignTargetsOutOfRange(5),
				alignInterStageSlopeOutOfRange(6),
				alignPilotsNotFound(7),
				alignInputSlopeOutOfRange(8),
				alignGainTargetOutOfRange(9),
				alignCableSimulatorNeeded(10),
				alignGainOrSlopeSaturated(11),
				alignUnknownForwardPathPlug(12),
				alignGain2TargetOutOfRange(13),
				alignInterStage2SlopeOutOfRange(14),
				alignOpticalInputPowerOutOfRange(15)
				}
			ACCESS read-only
			STATUS mandatory
			DESCRIPTION
				"Status of last return path automatic aligment:
				1 = never run
				2 = running
				3 = success
				4 = no tuner module
				5 = targets out of range
				6 = interstage slope target ouf of range
				7 = pilots not found
				8 = input slope out of range
				9 = gain target out of range
				10 = a cable simulator may be needed into the universal plug-in slot
				11 = gain or slope is saturated
				12 = unknown forward path plug-in module
				13 = alignGain2TargetOutOfRange
				14 = alignInterStage2SlopeOutOfRange
				15 = alignOpticalInputPowerOutOfRange"
			::= { acxReturnPath 8 }

		
		-- 1.3.6.1.4.1.3715.11.6.9
		acxReturnPathRoutingControl OBJECT-TYPE
			SYNTAX INTEGER
				{
				separateRfPaths(1),
				combinedRfPaths(2),
				separateRfPathsWithBackup(3),
				separateRfPathsWithBackupAndManualRestore(4),
				mode1(5),
				mode2(6),
				mode3(7),
				mode4(8),
				mode5(9),
				mode6(10),
				mode7(11),
				mode8(12),
				mode9(13),
				mode10(14),
				mode11(15),
				mode12(16)
				}
			ACCESS read-write
			STATUS mandatory
			DESCRIPTION
				"Return path routing control:
				1  = separate RF paths
				2  = combined RF paths
				3  = separate RF paths with backup
				4  = separate RF paths with backup and manual restore
				5  = RF1+RF2+RF3+RF4 to Tx1 (mode 1)
				6  = RF1+RF2 to Tx1, RF3+RF4 to Tx3 (mode 2)
				7  = RF1+RF4 to Tx1, RF2+RF3 to Tx2 (mode 3)
				8  = RF1 to Tx1, RF2 to Tx2, RF3+RF4 to Tx3 (mode 4)
				9  = RF1 to Tx1, RF2 to Tx2, RF3 to Tx3, RF4 to Tx4 (mode 5, different backup than mode 8)
				10 = RF1+RF2 to Tx1, RF3+RF4 to Tx2 (mode 6)
				11 = RF1+RF2 to Tx1, RF3 to Tx3, RF4 to Tx4 (mode 7)
				12 = RF1 to Tx1, RF2 to Tx2, RF3 to Tx3, RF4 to Tx4 (mode 8, different backup than mode 5)
				13 = RF1+RF2+RF3+RF4 to Tx1 (mode 9, different laser on functionality than mode 1)
				14 = RF1+RF2+RF3+RF4 to Tx1 (mode 10, different backup and different laser on functionality than mode 1)
				15 = RF1+RF2+RF3+RF4->Tx2 (mode 11) (AC9100 NEO only)
				16 = RF1+RF2->Tx2, RF3+RF4->Tx4 (mode 12) (AC9100 NEO only)
				"
			::= { acxReturnPath 9 }

		
		-- 1.3.6.1.4.1.3715.11.6.10
		acxReturnPathRoutingStatus OBJECT-TYPE
			SYNTAX INTEGER
				{
				separateRfPaths(1),
				combinedRfPaths(2),
				rf1rf2rf3rf4tx1(5),
				rf1rf2tx1andrf3rf4tx3(6),
				rf1rf4tx1andrf2rf3tx2(7),
				rf1tx1andrf2tx2andrf3rf4tx3(8),
				rf1tx1andrf2tx2andrf3tx3andrf4tx4(9),
				rf1rf2rf3rf4tx2(10),
				rf1rf2rf3rf4tx3(11),
				rf1rf4tx1andrf2tx2andrf3tx3(12),
				rf1rf4tx4andrf2tx2andrf3tx3(13),
				rf1tx1andrf2rf3tx2andrf4tx4(14),
				rf1tx1andrf2rf3tx3andrf4tx4(15),
				rf1rf4tx4andrf2rf3tx3(16),
				rf1rf2tx1andrf3rf4tx2(17),
				rf1rf2tx1andrf3tx3andrf4tx4(18),
				rf1rf2tx2andrf3tx3andrf4tx4(19),
				rf1tx1andrf2tx2andrf3rf4tx4(20),
				rf1rf2rf3rf4tx4(21),
				rf1rf2tx2rf3rf4tx4(22)
				}
			ACCESS read-only
			STATUS mandatory
			DESCRIPTION
				"Return path routing status:
				1  = separate RF paths
				2  = combined RF paths
				5  = RF1+RF2+RF3+RF4 to Tx1
				6  = RF1+RF2 to Tx1, RF3+RF4 to Tx3
				7  = RF1+RF4 to Tx1, RF2+RF3 to Tx2
				8  = RF1 to Tx1, RF2 to Tx2, RF3+RF4 to Tx3
				9  = RF1 to Tx1, RF2 to Tx2, RF3 to Tx3, RF4 to Tx4
				10 = RF1+RF2+RF3+RF4 to Tx2
				11 = RF1+RF2+RF3+RF4 to Tx3
				12 = RF1+RF4 to Tx1, RF2 to Tx2, RF3 to Tx3
				13 = RF1+RF4 to Tx4, RF2 to Tx2, RF3 to Tx3
				14 = RF1 to Tx1, RF2+RF3 to Tx2, RF4 to Tx4
				15 = RF1 to Tx1, RF2+RF3 to Tx3, RF4 to Tx4
				16 = RF1+RF4 to Tx4, RF2+RF3 to Tx3
				17 = RF1+RF2 to Tx1, RF3+RF4 to Tx2
				18 = RF1+RF2 to Tx1, RF3 to Tx3, RF4 to Tx4
				19 = RF1+RF2 to Tx2, RF3 to Tx3, RF4 to Tx4
				20 = RF1 to Tx1, RF2 to Tx2, RF3+RF4 to Tx4
				21 = RF1+RF2+RF3+RF4 to TX4
				22 = RF1+RF2 to TX2, RF3+RF4 to TX4"
			::= { acxReturnPath 10 }

		
		-- 1.3.6.1.4.1.3715.11.6.11
		acxReturnPathPowerSave OBJECT-TYPE
			SYNTAX INTEGER
				{
				powerSaveDisabled(1),
				powerSaveEnabled(2),
				powerSaveLaser1(3),
				powerSaveLaser2(4),
				powerSaveRfLaser(5)
				}
			ACCESS read-write
			STATUS mandatory
			DESCRIPTION
				"Power save mode for optical transmitters:
				1 = power save is disabled, RF stages and laser always on
				2 = power save is enabled for RF stages, laser always on
				3 = power save is enabled for RF stages and laser
				4 = power save is enabled for RF states and laser, only one laser is active
				5 = power save is enabled for RF stages and laser, when no RF signal is routed to optical transmitter
				When enabled, RF stages (and laser) of non-active optical 
				return transmitter are switched off."
			::= { acxReturnPath 11 }

		
		-- 1.3.6.1.4.1.3715.11.6.12
		acxNumberOfReturnPathOmiEntries OBJECT-TYPE
			SYNTAX INTEGER (0..8)
			ACCESS read-only
			STATUS mandatory
			DESCRIPTION
				"The number of entries in the acxReturnPathOmiAlignTable"
			::= { acxReturnPath 12 }

		
		-- 1.3.6.1.4.1.3715.11.6.13
		acxReturnPathOmiAlignTable OBJECT-TYPE
			SYNTAX SEQUENCE OF AcxReturnPathOmiAlignEntry
			ACCESS not-accessible
			STATUS mandatory
			DESCRIPTION
				"A table of return path OMI based alignment entries."
			::= { acxReturnPath 13 }

		
		-- 1.3.6.1.4.1.3715.11.6.13.1
		acxReturnPathOmiAlignEntry OBJECT-TYPE
			SYNTAX AcxReturnPathOmiAlignEntry
			ACCESS not-accessible
			STATUS mandatory
			INDEX { acxReturnPathOmiAlignIndex }
			::= { acxReturnPathOmiAlignTable 1 }

		
		AcxReturnPathOmiAlignEntry ::=
			SEQUENCE { 
				acxReturnPathOmiAlignIndex
					INTEGER,
				acxReturnPathOmiAlignTargetOmi
					INTEGER,
				acxReturnPathOmiAlignRfLevelReference
					INTEGER
			 }

		-- 1.3.6.1.4.1.3715.11.6.13.1.1
		acxReturnPathOmiAlignIndex OBJECT-TYPE
			SYNTAX INTEGER (1..10)
			ACCESS read-only
			STATUS mandatory
			DESCRIPTION
				"The table index. Please note that this index differs from the
				acxReturnTransmitterTable index, which is the module slot number.
				This index refers to the return transmitter'order number' the settings
				concern, e.g. index value 1 means transmitter 1 etc."
			::= { acxReturnPathOmiAlignEntry 1 }

		
		-- 1.3.6.1.4.1.3715.11.6.13.1.2
		acxReturnPathOmiAlignTargetOmi OBJECT-TYPE
			SYNTAX INTEGER
			ACCESS read-write
			STATUS mandatory
			DESCRIPTION
				"Return transmitter target OMI. This OMI is reached when the input
				RF level is equal to returnTransmitterRfLevelReference. Unit 0.01 %."
			::= { acxReturnPathOmiAlignEntry 2 }

		
		-- 1.3.6.1.4.1.3715.11.6.13.1.3
		acxReturnPathOmiAlignRfLevelReference OBJECT-TYPE
			SYNTAX INTEGER
			ACCESS read-write
			STATUS mandatory
			DESCRIPTION
				"Return transmitter RF level reference value for OMI control.
				When the input RF level has this value, transmitter OMI is set
				to the value given by returnTransmitterTargetOmi. Unit 0.01 dBuV."
			::= { acxReturnPathOmiAlignEntry 3 }

		
		-- 1.3.6.1.4.1.3715.11.6.14
		acxReturnPathBackupControl OBJECT-TYPE
			SYNTAX INTEGER
				{
				noBackup(1),
				autoRevertive(2),
				autoNonRevertive(3)
				}
			ACCESS read-write
			STATUS mandatory
			DESCRIPTION
				"Return path backup mode:
				1 = no backup
				2 = automatic, revertive
				3 = automatic, non-revertive"
			::= { acxReturnPath 14 }

		
		-- 1.3.6.1.4.1.3715.11.6.15
		acxReturnPathModemRouting OBJECT-TYPE
			SYNTAX INTEGER
			ACCESS read-write
			STATUS mandatory
			DESCRIPTION
				"Transponder transmit signal routing control.
				Bitmask. Bit set = transponder signal summed 
				to corresponding return path RF input signal.
				Bit 0 = Input 1
				Bit 1 = Input 2
				Bit 2 = Input 3
				Bit 3 = Input 4"
			::= { acxReturnPath 15 }

		
		-- 1.3.6.1.4.1.3715.11.6.16
		acxReturnPathNumberOfInputs OBJECT-TYPE
			SYNTAX INTEGER
			ACCESS read-only
			STATUS mandatory
			::= { acxReturnPath 16 }

		
		-- 1.3.6.1.4.1.3715.11.6.17
		acxReturnPathInputTable OBJECT-TYPE
			SYNTAX SEQUENCE OF AcxReturnPathInputEntry
			ACCESS not-accessible
			STATUS mandatory
			::= { acxReturnPath 17 }

		
		-- 1.3.6.1.4.1.3715.11.6.17.1
		acxReturnPathInputEntry OBJECT-TYPE
			SYNTAX AcxReturnPathInputEntry
			ACCESS not-accessible
			STATUS mandatory
			INDEX { moduleId }
			::= { acxReturnPathInputTable 1 }

		
		AcxReturnPathInputEntry ::=
			SEQUENCE { 
				acxReturnPathInputModemLevel
					INTEGER
			 }

		-- 1.3.6.1.4.1.3715.11.6.17.1.2
		acxReturnPathInputModemLevel OBJECT-TYPE
			SYNTAX INTEGER
			ACCESS read-only
			STATUS mandatory
			DESCRIPTION
				"Modem equivalent input level.
				The signal level needed at return path input to appear at same level 
				than modem transmit signal at return path output. Unit 0.01 dBµV"
			::= { acxReturnPathInputEntry 2 }

		
		-- 1.3.6.1.4.1.3715.11.6.18
		acxReturnPathOmiTestPointControl OBJECT-TYPE
			SYNTAX INTEGER
				{
				omiTestPointNA(1),
				omiTestPointAutomatic(2),
				omiTestPointTx1(3),
				omiTestPointTx2(4),
				omiTestPointTx3(5),
				omiTestPointTx4(6)
				}
			ACCESS read-write
			STATUS mandatory
			DESCRIPTION
				"OMI test point control.
				1: OMI test point control not available.
				2: Automatic OMI test point control. OMI test point is automatically in round robin.
				3: Transmitter 1
				4: Transmitter 2
				5: Transmitter 3
				6: Transmitter 4
				"
			::= { acxReturnPath 18 }

		
		-- 1.3.6.1.4.1.3715.11.7
		acxIngressSwitch OBJECT IDENTIFIER ::= { acx 7 }

		
		-- 1.3.6.1.4.1.3715.11.7.1
		acxNumberOfIngressSwitches OBJECT-TYPE
			SYNTAX INTEGER (0..8)
			ACCESS read-only
			STATUS mandatory
			DESCRIPTION
				"The number of ingress switches available in the device."
			::= { acxIngressSwitch 1 }

		
		-- 1.3.6.1.4.1.3715.11.7.2
		acxIngressSwitchTable OBJECT-TYPE
			SYNTAX SEQUENCE OF AcxIngressSwitchEntry
			ACCESS not-accessible
			STATUS mandatory
			DESCRIPTION
				"A table of ingress switches available in this device."
			::= { acxIngressSwitch 2 }

		
		-- 1.3.6.1.4.1.3715.11.7.2.1
		acxIngressSwitchEntry OBJECT-TYPE
			SYNTAX AcxIngressSwitchEntry
			ACCESS not-accessible
			STATUS mandatory
			INDEX { acxIngressSwitchIndex }
			::= { acxIngressSwitchTable 1 }

		
		AcxIngressSwitchEntry ::=
			SEQUENCE { 
				acxIngressSwitchIndex
					INTEGER,
				acxIngressSwitchMode
					INTEGER,
				acxIngressSwitchAttenuation
					INTEGER
			 }

		-- 1.3.6.1.4.1.3715.11.7.2.1.1
		acxIngressSwitchIndex OBJECT-TYPE
			SYNTAX INTEGER (1..8)
			ACCESS read-only
			STATUS mandatory
			DESCRIPTION
				"Index of the ingress switch."
			::= { acxIngressSwitchEntry 1 }

		
		-- 1.3.6.1.4.1.3715.11.7.2.1.2
		acxIngressSwitchMode OBJECT-TYPE
			SYNTAX INTEGER
				{
				on(1),
				attenuator(2),
				off(3)
				}
			ACCESS read-write
			STATUS mandatory
			DESCRIPTION
				"Return path ingress switch state:
				1 = ON (0 dB)
				2 = attenuator
				3 = OFF (<-45 dB)
				This object has an entry in the discretePropertyTable."
			::= { acxIngressSwitchEntry 2 }

		
		-- 1.3.6.1.4.1.3715.11.7.2.1.3
		acxIngressSwitchAttenuation OBJECT-TYPE
			SYNTAX INTEGER
			ACCESS read-write
			STATUS mandatory
			DESCRIPTION
				"Attenuation value of the ingress switch mode 'attenuator'. Unit 0.01 dB."
			::= { acxIngressSwitchEntry 3 }

		
		-- 1.3.6.1.4.1.3715.11.7.3
		acxIngressSwitchControlMode OBJECT-TYPE
			SYNTAX INTEGER
				{
				ingressSwitchControlModeAlarmAttenuate(1),
				ingressSwitchControlModeManual(2),
				ingressSwitchControlModeAlarmOff(3),
				ingressSwitchControlModeWarningAttenuateAlarmOff(4)
				}
			ACCESS read-write
			STATUS mandatory
			DESCRIPTION
				"Ingress switch control mode.
				
				1: Ingress switch (ICS) is automatically switched to attenuation/padding (typically -6 dB) when ingress alarm is active.
				2: Ingress switch controlled manually.
				3: Ingress switch (ICS) is automatically switched to off (typically -50 dB) when ingress alarm is active.
				4: Ingress switch (ICS) is automatically switched to attenuation/padding (typically -6 dB) when ingress warning is active and 
				   Ingress switch (ICS) is automatically switched to off (typically -50 dB) when ingress alarm is active.
				 	
				 See also ingressSwitchControlModeVersion for supported modes.
				"
			::= { acxIngressSwitch 3 }

		
		-- 1.3.6.1.4.1.3715.11.7.4
		acxIngressSwitchActivationDelay OBJECT-TYPE
			SYNTAX INTEGER
			ACCESS read-write
			STATUS mandatory
			DESCRIPTION
				"Activation delay of the automatic ingress attenuation function.
				Unit 1 second."
			::= { acxIngressSwitch 4 }

		
		-- 1.3.6.1.4.1.3715.11.7.5
		acxIngressSwitchDeactivationDelay OBJECT-TYPE
			SYNTAX INTEGER
			ACCESS read-write
			STATUS mandatory
			DESCRIPTION
				"Deactivation delay of the automatic ingress attenuation function.
				Unit 1 second."
			::= { acxIngressSwitch 5 }

		
		-- 1.3.6.1.4.1.3715.11.7.6
		acxIngressSwitchControlModeVersion OBJECT-TYPE
			SYNTAX INTEGER
				{
				ingressSwitchControlModeVersion2(2),
				ingressSwitchControlModeVersion4(4)
				}
			ACCESS read-only
			STATUS mandatory
			DESCRIPTION
				"Number of modes supported by ingressSwitchControlMode.
				- If this OID is unavailable, legacy mode is supported: 1 and 2.
				- 2: Legacy mode is supported: 1 and 2.
				 - 4: New modes (3 and 4) are supported in addition to legacy modes 1 and 2.
				 	
				Mode enumerations
				- ingressSwitchControlModeAlarmAttenuate(1),
				- ingressSwitchControlModeManual(2),
				- ingressSwitchControlModeAlarmOff(3),
				- ingressSwitchControlModeWarningAttenuateAlarmOff(4)"
			::= { acxIngressSwitch 6 }

		
		-- 1.3.6.1.4.1.3715.11.8
		acxAlsc OBJECT IDENTIFIER ::= { acx 8 }

		
		-- 1.3.6.1.4.1.3715.11.8.2
		acxNumberOfAlscModules OBJECT-TYPE
			SYNTAX INTEGER (0..8)
			ACCESS read-only
			STATUS mandatory
			DESCRIPTION
				"Number of ALSC modules in this device. Zero means 
				that the ALSC function is not available."
			::= { acxAlsc 2 }

		
		-- 1.3.6.1.4.1.3715.11.8.3
		acxAlscControlMode OBJECT-TYPE
			SYNTAX INTEGER
				{
				modeAlsc(1),
				modeManual(2),
				modeIntelligent(3),
				modeOLC(5)
				}
			ACCESS read-write
			STATUS mandatory
			DESCRIPTION
				"ALSC operating mode:
				1 = ALSC, gain and slope controls are adjusted automatically based on pilot levels
				2 = Gain and slope controls are be adjusted manually
				3 = Total gain can be adjusted manually, individual gain control elements
				    are adjusted automatically based on it. Slope controls are adjusted manually.
				5 = Optical Level Control mode."
			::= { acxAlsc 3 }

		
		-- 1.3.6.1.4.1.3715.11.8.4
		acxAlscTargetLevelTable OBJECT-TYPE
			SYNTAX SEQUENCE OF AcxAlscTargetLevelEntry
			ACCESS not-accessible
			STATUS mandatory
			DESCRIPTION
				"A table of ALSC target levels entries."
			::= { acxAlsc 4 }

		
		-- 1.3.6.1.4.1.3715.11.8.4.1
		acxAlscTargetLevelEntry OBJECT-TYPE
			SYNTAX AcxAlscTargetLevelEntry
			ACCESS not-accessible
			STATUS mandatory
			INDEX { acxLevelDetectorIndex }
			::= { acxAlscTargetLevelTable 1 }

		
		AcxAlscTargetLevelEntry ::=
			SEQUENCE { 
				acxAlscTargetLevelValue
					INTEGER,
				acxAlscTargetLevelUse
					INTEGER,
				acxAlscTargetLevelBackoff
					INTEGER,
				acxAlscTargetLevelPrevAmp
					INTEGER
			 }

		-- 1.3.6.1.4.1.3715.11.8.4.1.1
		acxAlscTargetLevelValue OBJECT-TYPE
			SYNTAX INTEGER
			ACCESS read-write
			STATUS mandatory
			DESCRIPTION
				"Pilot target level value. Unit 0.01 dBuV."
			::= { acxAlscTargetLevelEntry 1 }

		
		-- 1.3.6.1.4.1.3715.11.8.4.1.2
		acxAlscTargetLevelUse OBJECT-TYPE
			SYNTAX INTEGER
				{
				useActive(1),
				useStandby(2),
				useDisabled(3),
				useLost(4),
				useActiveAndControlGain(5),
				useActiveAndControlSlope(6),
				useUnknown(7)
				}
			ACCESS read-only
			STATUS mandatory
			DESCRIPTION
				"This object tells if the pilot is used for ALSC or not.
				1 = Pilot is in use and controlling ALSC
				2 = Pilot is not in use (backup or missing)
				3 = Pilot is disabled
				4 = Pilot is lost
				5 = Pilot is in use and controlling gain 
				6 = Pilot is in use and controlling slope
				7 = Pilot usage unknown"
			::= { acxAlscTargetLevelEntry 2 }

		
		-- 1.3.6.1.4.1.3715.11.8.4.1.3
		acxAlscTargetLevelBackoff OBJECT-TYPE
			SYNTAX INTEGER (-1500..500)
			ACCESS read-write
			STATUS mandatory
			DESCRIPTION
				"Pilot target level backoff value. Unit 0.01 dB."
			::= { acxAlscTargetLevelEntry 3 }

		
		-- 1.3.6.1.4.1.3715.11.8.4.1.4
		acxAlscTargetLevelPrevAmp OBJECT-TYPE
			SYNTAX INTEGER
			ACCESS read-write
			STATUS mandatory
			DESCRIPTION
				"Pilot target level value of the previous amplifier in cascade. Unit 0.01 dBuV."
			::= { acxAlscTargetLevelEntry 4 }

		
		-- 1.3.6.1.4.1.3715.11.8.8
		acxAlscStatus OBJECT-TYPE
			SYNTAX INTEGER
				{
				alscNormal(1),
				alscMainPilotsMissing(2),
				alscOnePilotOnly(3),
				alscAllPilotsMissing(4),
				alscTunerError(5),
				alscDisabled(6)
				}
			ACCESS read-only
			STATUS mandatory
			DESCRIPTION
				"ALSC control status:
				1 = ALSC is functioning normally
				2 = ALSC is running on backup pilots
				3 = ALSC is running on one pilot only
				4 = all pilots are missing
				5 = internal error detected in the tuner unit
				6 = ALSC is switched off"
			::= { acxAlsc 8 }

		
		-- 1.3.6.1.4.1.3715.11.8.9
		acxAlscGainDefault OBJECT-TYPE
			SYNTAX INTEGER
			ACCESS read-write
			STATUS mandatory
			DESCRIPTION
				"'Go to' gain value used when all pilots are lost. Unit 0.01 dB."
			::= { acxAlsc 9 }

		
		-- 1.3.6.1.4.1.3715.11.8.10
		acxAlscSlopeDefault OBJECT-TYPE
			SYNTAX INTEGER
			ACCESS read-write
			STATUS mandatory
			DESCRIPTION
				"'Go to' slope/gain2 value used when all pilots are lost. Unit 0.01 dB."
			::= { acxAlsc 10 }

		
		-- 1.3.6.1.4.1.3715.11.8.11
		acxAlscGainStatus OBJECT-TYPE
			SYNTAX INTEGER
				{
				normal(1),
				minimum(2),
				maximum(3),
				frozen(4),
				default(5),
				saturatedAtMinimum(6),
				saturatedAtMaximum(7)
				}
			ACCESS read-only
			STATUS mandatory
			DESCRIPTION
				"Gain control status:
				1 = normal
				2 = minimum (control at minimum, but no request to adjust under minimum)
				3 = maximum (control at maximum, but no request to adjust over maximum)
				4 = frozen (ALSC on but no pilots are detected)
				5 = default (ALSC on but no pilots are detected)
				6 = saturatedAtMinimum (control saturated at minimum value, but there's need to adjust under minimum)
				7 = saturatedAtMaximum (control saturated at maximum value, but there's need to adjust over maximum)
				
				This object has an entry in the discretePropertyTable.
				
				Returns value normal(1) when ALSC is not enabled."
			::= { acxAlsc 11 }

		
		-- 1.3.6.1.4.1.3715.11.8.12
		acxAlscSlopeStatus OBJECT-TYPE
			SYNTAX INTEGER
				{
				normal(1),
				minimum(2),
				maximum(3),
				frozen(4),
				default(5),
				saturatedAtMinimum(6),
				saturatedAtMaximum(7)
				}
			ACCESS read-only
			STATUS mandatory
			DESCRIPTION
				"Slope/gain2 control status:
				1 = normal
				2 = minimum (control at minimum, but no request to adjust under minimum)
				3 = maximum (control at maximum, but no request to adjust over maximum)
				4 = frozen (ALSC on but no pilots are detected)
				5 = default (ALSC on but no pilots are detected)
				6 = saturatedAtMinimum (control saturated at minimum value, but there's need to adjust under minimum)
				7 = saturatedAtMaximum (control saturated at maximum value, but there's need to adjust over maximum)
				
				This object has an entry in the discretePropertyTable.
				
				Returns value normal(1) when ALSC is not enabled."
			::= { acxAlsc 12 }

		
		-- 1.3.6.1.4.1.3715.11.8.13
		acxAlscPilotLostAction OBJECT-TYPE
			SYNTAX INTEGER
				{
				freeze(1),
				preset(2)
				}
			ACCESS read-write
			STATUS mandatory
			DESCRIPTION
				"ALSC behaviour when all pilots are lost.
				1 = freeze gain and slope to current values
				2 = set gain and slope to preset values (acxAlscGainDefault1/2)"
			::= { acxAlsc 13 }

		
		-- 1.3.6.1.4.1.3715.11.8.14
		acxAlscPilotLostLimit OBJECT-TYPE
			SYNTAX INTEGER
			ACCESS read-write
			STATUS mandatory
			DESCRIPTION
				"The level value under which a pilot is declared as lost. This value is
				common to alla pilots. Unit 0.01 dBuV.
				
				Newer products use individual lost levels for each pilot. With 
				these products lost levels are defined in acxLevelDetectorTable."
			::= { acxAlsc 14 }

		
		-- 1.3.6.1.4.1.3715.11.8.15
		acxAlscControlStatus OBJECT-TYPE
			SYNTAX INTEGER
				{
				controlsOk(1),
				controlsSaturated(2)
				}
			ACCESS read-only
			STATUS mandatory
			DESCRIPTION
				"Gain and Slope control status:
				1 = Gain and slope control are within control range
				2 = One or both controls are saturated"
			::= { acxAlsc 15 }

		
		-- 1.3.6.1.4.1.3715.11.9
		acxSignalMonitor OBJECT IDENTIFIER ::= { acx 9 }

		
		-- 1.3.6.1.4.1.3715.11.9.1
		acxNumberOfLevelDetectors OBJECT-TYPE
			SYNTAX INTEGER (0..8)
			ACCESS read-only
			STATUS mandatory
			DESCRIPTION
				"Number of signal monitors in this device.
				0 = No signal monitors are available."
			::= { acxSignalMonitor 1 }

		
		-- 1.3.6.1.4.1.3715.11.9.2
		acxLevelDetectorTable OBJECT-TYPE
			SYNTAX SEQUENCE OF AcxLevelDetectorEntry
			ACCESS not-accessible
			STATUS mandatory
			DESCRIPTION
				"A table of level detector entries."
			::= { acxSignalMonitor 2 }

		
		-- 1.3.6.1.4.1.3715.11.9.2.1
		acxLevelDetectorEntry OBJECT-TYPE
			SYNTAX AcxLevelDetectorEntry
			ACCESS not-accessible
			STATUS mandatory
			INDEX { acxLevelDetectorIndex }
			::= { acxLevelDetectorTable 1 }

		
		AcxLevelDetectorEntry ::=
			SEQUENCE { 
				acxLevelDetectorIndex
					INTEGER,
				acxLevelDetectorFrequency
					INTEGER,
				acxLevelDetectorUsage
					INTEGER,
				acxLevelDetectorMode
					INTEGER,
				acxLevelDetectorValue
					INTEGER,
				acxLevelDetectorStatus
					ValueStatus,
				acxLevelDetectorLostLevel
					INTEGER,
				acxLevelDetectorSupportedModes
					INTEGER
			 }

		-- 1.3.6.1.4.1.3715.11.9.2.1.1
		acxLevelDetectorIndex OBJECT-TYPE
			SYNTAX INTEGER (1..5)
			ACCESS read-only
			STATUS mandatory
			DESCRIPTION
				"Index to the level detector table."
			::= { acxLevelDetectorEntry 1 }

		
		-- 1.3.6.1.4.1.3715.11.9.2.1.2
		acxLevelDetectorFrequency OBJECT-TYPE
			SYNTAX INTEGER
			ACCESS read-write
			STATUS mandatory
			DESCRIPTION
				"Level detector frequency. Unit kHz.
				0 = Wideband detector (read-only)."
			::= { acxLevelDetectorEntry 2 }

		
		-- 1.3.6.1.4.1.3715.11.9.2.1.3
		acxLevelDetectorUsage OBJECT-TYPE
			SYNTAX INTEGER
				{
				other(1),
				pilotHighMain(2),
				pilotHighReserve(3),
				pilotLowMain(4),
				pilotLowReserve(5),
				monitorSignal(6),
				monitorWideband(7)
				}
			ACCESS read-only
			STATUS mandatory
			DESCRIPTION
				"Use of the level measurement:
				1 = Other
				2 = Main high pilot
				3 = Reserve high pilot
				4 = Main low pilot
				5 = Reserve low pilot
				6 = Signal monitor
				7 = Wideband signal monitor
				
				Target levels in the acxAlscTargetLevelTable exist only
				for entry types 2...5."
			::= { acxLevelDetectorEntry 3 }

		
		-- 1.3.6.1.4.1.3715.11.9.2.1.4
		acxLevelDetectorMode OBJECT-TYPE
			SYNTAX INTEGER
				{
				modeAnalog(1),
				modeQam(2),
				modeWideband(3),
				modeAnnexB(4),
				modeOFDM(5),
				modeMinHold(6),
				modeMaxHold(7),
				modeUnset(16)
				}
			ACCESS read-write
			STATUS mandatory
			DESCRIPTION
				"Level detector operating mode:
				1 = peak hold for analogue TV channel or carrier (pilot)
				2 = average for QAM (EU)/AnnexA (6.875 MHz) channel or noise
				3 = wideband signal power monitor (read only)
				4 = average for QAM (US)/AnnexB (5.4 MHz) channel
				5 = average for QFDM (6.0 MHz) channel
				6 = MinHold
				7 = MaxHold
				16 = operating mode is not set or is unknown."
			::= { acxLevelDetectorEntry 4 }

		
		-- 1.3.6.1.4.1.3715.11.9.2.1.5
		acxLevelDetectorValue OBJECT-TYPE
			SYNTAX INTEGER
			ACCESS read-only
			STATUS mandatory
			DESCRIPTION
				"Measured signal level. Unit 0.01 dBuV (dB for wideband signal monitor).
				This object has an entry in the propertyTable (only instances with 
				acxLevelDetectorUsage values 6(monitorSignal) or 7(monitorWideband))."
			::= { acxLevelDetectorEntry 5 }

		
		-- 1.3.6.1.4.1.3715.11.9.2.1.6
		acxLevelDetectorStatus OBJECT-TYPE
			SYNTAX ValueStatus
			ACCESS read-only
			STATUS mandatory
			DESCRIPTION
				"Measured signal level status:
				1 = normal
				2 = HIHI
				3 = HI
				4 = LO
				5 = LOLO
				This object has an entry in the discretePropertyTable (only instances with 
				acxLevelDetectorUsage values 2...5 (pilots))."
			::= { acxLevelDetectorEntry 6 }

		
		-- 1.3.6.1.4.1.3715.11.9.2.1.7
		acxLevelDetectorLostLevel OBJECT-TYPE
			SYNTAX INTEGER
			ACCESS read-write
			STATUS mandatory
			DESCRIPTION
				"A level value below which the signal is declared as 'lost'.
				Unit 0.01 dBuV."
			::= { acxLevelDetectorEntry 7 }

		
		-- 1.3.6.1.4.1.3715.11.9.2.1.8
		acxLevelDetectorSupportedModes OBJECT-TYPE
			SYNTAX INTEGER
			ACCESS read-only
			STATUS mandatory
			DESCRIPTION
				"Supported acxLevelDetectorModes. This is bitfield.
				 	
				0x01: Legacy analog and digital/AnnexA/EU QAM supported.
				0x02: Annex B/US QAM and OFDM supported.
				0x04: MinHold and MaxHold supported."
			::= { acxLevelDetectorEntry 8 }

		
		-- 1.3.6.1.4.1.3715.11.11
		acxSpectrumAnalyser OBJECT IDENTIFIER ::= { acx 11 }

		
		-- 1.3.6.1.4.1.3715.11.11.1
		acxNumberOfSpectrumAnalysers OBJECT-TYPE
			SYNTAX INTEGER (0..8)
			ACCESS read-only
			STATUS mandatory
			DESCRIPTION
				"The number of spectrum analysers in this device.
				0 = no signal monitors are available."
			::= { acxSpectrumAnalyser 1 }

		
		-- 1.3.6.1.4.1.3715.11.11.2
		acxSpectrumAnalyserMode OBJECT-TYPE
			SYNTAX INTEGER
				{
				on(1),
				off(2),
				restart(3)
				}
			ACCESS read-write
			STATUS mandatory
			DESCRIPTION
				"Spectrum analyser mode:
				1 = OFF
				2 = ON
				3 = restart scanning"
			::= { acxSpectrumAnalyser 2 }

		
		-- 1.3.6.1.4.1.3715.11.11.3
		acxSpectrumAnalyserChannelTableName OBJECT-TYPE
			SYNTAX OCTET STRING (SIZE (0..20))
			ACCESS read-write
			STATUS mandatory
			DESCRIPTION
				"Name of the channel table file."
			::= { acxSpectrumAnalyser 3 }

		
		-- 1.3.6.1.4.1.3715.11.11.4
		acxSpectrumAnalyserChannelTable OBJECT-TYPE
			SYNTAX OCTET STRING (SIZE (400))
			ACCESS read-write
			STATUS mandatory
			DESCRIPTION
				"A string of spectrum analyser measurement frequencies.
				Each octet pair in the string represents one frequency value 
				as a multiple of 0.25 MHz, starting from the lowest frequency."
			::= { acxSpectrumAnalyser 4 }

		
		-- 1.3.6.1.4.1.3715.11.11.5
		acxSpectrumAnalyserChannelTypeTable OBJECT-TYPE
			SYNTAX OCTET STRING (SIZE (25))
			ACCESS read-write
			STATUS mandatory
			DESCRIPTION
				"A string of spectrum analyser detector modes. Bitwise encoding, 
				each bit tells the detector mode for one of the corresponding 
				frequency in acxSpAnalyserChannelTable.
				Bit value 0 = PAL
				Bit value 1 = QAM"
			::= { acxSpectrumAnalyser 5 }

		
		-- 1.3.6.1.4.1.3715.11.11.6
		acxSpectrumAnalyserValueTable OBJECT-TYPE
			SYNTAX OCTET STRING (SIZE (200))
			ACCESS read-only
			STATUS mandatory
			DESCRIPTION
				"A string of spectrum analyser level measurement values.
				Each octet in the string represents the level of the
				corresponding frequency in acxSpectrumAnalyserChannelTable.
				Unit 0.5 dBuV."
			::= { acxSpectrumAnalyser 6 }

		
		-- 1.3.6.1.4.1.3715.11.11.7
		acxSpectrumAnalyserLowLimitTable OBJECT-TYPE
			SYNTAX OCTET STRING (SIZE (200))
			ACCESS read-write
			STATUS mandatory
			DESCRIPTION
				"A string of spectrum analyser level low limit values.
				Each octet in the string represents the low limit value 
				of the corresponding frequency in acxSpectrumAnalyserChannelTable.
				Unit 0.5 dBuV.
				Value 0xFF indicates a non-used limit value."
			::= { acxSpectrumAnalyser 7 }

		
		-- 1.3.6.1.4.1.3715.11.11.8
		acxSpectrumAnalyserHighLimitTable OBJECT-TYPE
			SYNTAX OCTET STRING (SIZE (200))
			ACCESS read-write
			STATUS mandatory
			DESCRIPTION
				"A string of spectrum analyser level high limit values.
				Each octet in the string represents the high limit value 
				of the corresponding frequency in acxSpectrumAnalyserChannelTable.
				Unit 0.5 dBuV.
				Value 0xFF indicates a non-used limit value."
			::= { acxSpectrumAnalyser 8 }

		
		-- 1.3.6.1.4.1.3715.11.11.9
		acxSpectrumAnalyserAlarmThreshold OBJECT-TYPE
			SYNTAX INTEGER (0..200)
			ACCESS read-write
			STATUS mandatory
			DESCRIPTION
				"The number of limits exceeded before a spectrum alarm is activated."
			::= { acxSpectrumAnalyser 9 }

		
		-- 1.3.6.1.4.1.3715.11.11.10
		acxSpectrumAnalyserSweepTime OBJECT-TYPE
			SYNTAX INTEGER
			ACCESS read-only
			STATUS mandatory
			DESCRIPTION
				"Spectrum analyser sweep time. Unit 1 second."
			::= { acxSpectrumAnalyser 10 }

		
		-- 1.3.6.1.4.1.3715.11.11.11
		acxSpectrumAnalyserStatus OBJECT-TYPE
			SYNTAX INTEGER
				{
				noAlarm(1),
				alarm(2)
				}
			ACCESS read-only
			STATUS mandatory
			DESCRIPTION
				"Spectrum status:
				1 = no more than 'acxSpectrumAnalyserAlarmThreshold' measurements exceed their limits
				2 = more than 'acxSpectrumAnalyserAlarmThreshold' measurements exceed their limits
				This object has an entry in the discretePropertyTable."
			::= { acxSpectrumAnalyser 11 }

		
		-- 1.3.6.1.4.1.3715.11.50
		acxTransponder OBJECT IDENTIFIER ::= { acx 50 }

		
		-- 1.3.6.1.4.1.3715.11.50.1
		acxTransponderFunctionStatus OBJECT-TYPE
			SYNTAX INTEGER
				{
				running(1),
				notRunning(2)
				}
			ACCESS read-only
			STATUS obsolete
			DESCRIPTION
				"Status of the internal function file:
				1 = running
				2 = not running"
			::= { acxTransponder 1 }

		
		-- 1.3.6.1.4.1.3715.11.50.2
		acxTransponderFunctionCrc OBJECT-TYPE
			SYNTAX INTEGER
			ACCESS read-only
			STATUS obsolete
			DESCRIPTION
				"CRC value of the function file."
			::= { acxTransponder 2 }

		
		-- 1.3.6.1.4.1.3715.11.50.3
		acxTransponderStatus OBJECT-TYPE
			SYNTAX INTEGER
				{
				statusNormal(1),
				statusInternalError(2),
				statusUnknownModule(3),
				statusNotPowered(4)
				}
			ACCESS read-only
			STATUS obsolete
			DESCRIPTION
				"Transponder general status
				1 = transponder is working normally
				2 = internal error in transponder
				3 = one or more unknown modules are present
				4 = transponder partially powered, no full functionality"
			::= { acxTransponder 3 }

		
		-- 1.3.6.1.4.1.3715.11.500
		ac500 OBJECT IDENTIFIER ::= { acx 500 }

		
		-- 1.3.6.1.4.1.3715.11.501
		ac500i OBJECT IDENTIFIER ::= { acx 501 }

		
		-- 1.3.6.1.4.1.3715.11.800
		ac800 OBJECT IDENTIFIER ::= { acx 800 }

		
		-- 1.3.6.1.4.1.3715.11.801
		ac800i OBJECT IDENTIFIER ::= { acx 801 }

		
		-- 1.3.6.1.4.1.3715.11.802
		ac800Z OBJECT IDENTIFIER ::= { acx 802 }

		
		-- 1.3.6.1.4.1.3715.11.1000
		ac1000 OBJECT IDENTIFIER ::= { acx 1000 }

		
		-- 1.3.6.1.4.1.3715.11.1001
		ac1000T OBJECT IDENTIFIER ::= { acx 1001 }

		
		-- 1.3.6.1.4.1.3715.11.1002
		ac1000i OBJECT IDENTIFIER ::= { acx 1002 }

		
		-- 1.3.6.1.4.1.3715.11.1500
		ac1500 OBJECT IDENTIFIER ::= { acx 1500 }

		
		-- 1.3.6.1.4.1.3715.11.2000
		ac2000 OBJECT IDENTIFIER ::= { acx 2000 }

		
		-- 1.3.6.1.4.1.3715.11.2001
		ac2000T OBJECT IDENTIFIER ::= { acx 2001 }

		
		-- 1.3.6.1.4.1.3715.11.2002
		ac2000i OBJECT IDENTIFIER ::= { acx 2002 }

		
		-- 1.3.6.1.4.1.3715.11.2500
		ac2500 OBJECT IDENTIFIER ::= { acx 2500 }

		
		-- 1.3.6.1.4.1.3715.11.3000
		ac3000 OBJECT IDENTIFIER ::= { acx 3000 }

		
		-- 1.3.6.1.4.1.3715.11.3000.606
		ac3000-606 OBJECT IDENTIFIER ::= { ac3000 606 }

		
		-- 1.3.6.1.4.1.3715.11.3001
		ac3000-1stgen OBJECT IDENTIFIER ::= { acx 3001 }

		
		-- 1.3.6.1.4.1.3715.11.3001.606
		ac3000-606-1stgen OBJECT IDENTIFIER ::= { ac3000-1stgen 606 }

		
		-- 1.3.6.1.4.1.3715.11.3002
		ac3000-2ndgen OBJECT IDENTIFIER ::= { acx 3002 }

		
		-- 1.3.6.1.4.1.3715.11.3002.606
		ac3000-606-2ndgen OBJECT IDENTIFIER ::= { ac3000-2ndgen 606 }

		
		-- 1.3.6.1.4.1.3715.11.3010
		ac3010 OBJECT IDENTIFIER ::= { acx 3010 }

		
		-- 1.3.6.1.4.1.3715.11.3010.1
		ac3010preSlope1GHz OBJECT-TYPE
			SYNTAX INTEGER
				{
				preSlopeFlat(1),
				preSloped(2)
				}
			ACCESS read-write
			STATUS mandatory
			DESCRIPTION
				"Forward path fixed 1.0 GHz preslope.
				
				Enumeration
				2: Enable 1.0 GHz preslope.
				1: Disable 1.0 GHz preslope."
			::= { ac3010 1 }

		
		-- 1.3.6.1.4.1.3715.11.3010.2
		ac3010trunkDistributionSelection OBJECT-TYPE
			SYNTAX INTEGER
				{
				flat(1),
				trunk(2)
				}
			ACCESS read-write
			STATUS mandatory
			DESCRIPTION
				"Distribution/flat vs. trunk selection.
				
				Enumeration
				2: Trunk.
				1: Distribution/flat."
			::= { ac3010 2 }

		
		-- 1.3.6.1.4.1.3715.11.3010.3
		ac3010inputBypassOutput3Selection OBJECT-TYPE
			SYNTAX INTEGER
				{
				inputBypass(1),
				output3(2),
				forcedInputBypass(3),
				forcedOutput3(4),
				other(5),
				unknown(6),
				notAvailable(7)
				}
			ACCESS read-write
			STATUS mandatory
			DESCRIPTION
				"Port 3 mode selection.
				
				Enumeration
				1: input bypass, 
				2: output 3, 
				3: forced input bypass, 
				4: forced output 3, 
				5: other, 
				6: unknown, 
				7: N/A"
			::= { ac3010 3 }

		
		-- 1.3.6.1.4.1.3715.11.3010.4
		ac3010irpc OBJECT-TYPE
			SYNTAX INTEGER
				{
				ac3010irpcEnabled(1),
				ac3010irpcDisabled(2)
				}
			ACCESS read-write
			STATUS mandatory
			DESCRIPTION
				"Intelligent return path level and slope control. 
				iRPC: intelligent Return Path Control.
				
				1: Enabled
				2: Disabled"
			::= { ac3010 4 }

		
		-- 1.3.6.1.4.1.3715.11.3010.3010
		ac3010-generations OBJECT IDENTIFIER ::= { ac3010 3010 }

		
		-- 1.3.6.1.4.1.3715.11.3010.3010.1
		ac3010-1stgen OBJECT IDENTIFIER ::= { ac3010-generations 1 }

		
		-- 1.3.6.1.4.1.3715.11.3010.3010.2
		ac3010-2ndgen OBJECT IDENTIFIER ::= { ac3010-generations 2 }

		
		-- 1.3.6.1.4.1.3715.11.3010.3010.3
		ac3010-3rdgen OBJECT IDENTIFIER ::= { ac3010-generations 3 }

		
		-- 1.3.6.1.4.1.3715.11.3020
		ac3020 OBJECT IDENTIFIER ::= { acx 3020 }

		
		-- 1.3.6.1.4.1.3715.11.3020.1
		ac3020preSlope1GHz OBJECT-TYPE
			SYNTAX INTEGER
				{
				preSlopeFlat(1),
				preSloped(2)
				}
			ACCESS read-write
			STATUS mandatory
			DESCRIPTION
				"Forward path fixed 1.0 GHz preslope.
				
				Enumeration
				2: Enable 1.0 GHz preslope.
				1: Disable 1.0 GHz preslope."
			::= { ac3020 1 }

		
		-- 1.3.6.1.4.1.3715.11.3020.2
		ac3020trunkDistributionSelection OBJECT-TYPE
			SYNTAX INTEGER
				{
				flat(1),
				trunk(2)
				}
			ACCESS read-write
			STATUS mandatory
			DESCRIPTION
				"Distribution/flat vs. trunk selection.
				
				Enumeration
				2: Trunk.
				1: Distribution/flat."
			::= { ac3020 2 }

		
		-- 1.3.6.1.4.1.3715.11.3020.3
		ac3020inputBypassOutput3Selection OBJECT-TYPE
			SYNTAX INTEGER
				{
				inputBypass(1),
				output3(2),
				forcedInputBypass(3),
				forcedOutput3(4),
				other(5),
				unknown(6),
				notAvailable(7)
				}
			ACCESS read-write
			STATUS mandatory
			DESCRIPTION
				"Port 3 mode selection.
				
				Enumeration
				1: input bypass, 
				2: output 3, 
				3: forced input bypass, 
				4: forced output 3, 
				5: other, 
				6: unknown, 
				7: N/A"
			::= { ac3020 3 }

		
		-- 1.3.6.1.4.1.3715.11.3020.4
		ac3020irpc OBJECT-TYPE
			SYNTAX INTEGER
				{
				ac3020irpcEnabled(1),
				ac3020irpcDisabled(2)
				}
			ACCESS read-write
			STATUS mandatory
			DESCRIPTION
				"Intelligent return path level and slope control. 
				iRPC: intelligent Return Path Control.
				
				1: Enabled
				2: Disabled"
			::= { ac3020 4 }

		
		-- 1.3.6.1.4.1.3715.11.3080
		ac3080 OBJECT IDENTIFIER ::= { acx 3080 }

		
		-- 1.3.6.1.4.1.3715.11.3080.3080
		ac3080-generations OBJECT IDENTIFIER ::= { ac3080 3080 }

		
		-- 1.3.6.1.4.1.3715.11.3080.3080.1
		ac3080-1stgen OBJECT IDENTIFIER ::= { ac3080-generations 1 }

		
		-- 1.3.6.1.4.1.3715.11.3200
		ac3200 OBJECT IDENTIFIER ::= { acx 3200 }

		
		-- 1.3.6.1.4.1.3715.11.3200.606
		ac3200-606 OBJECT IDENTIFIER ::= { ac3200 606 }

		
		-- 1.3.6.1.4.1.3715.11.3201
		ac3200-1stgen OBJECT IDENTIFIER ::= { acx 3201 }

		
		-- 1.3.6.1.4.1.3715.11.3201.606
		ac3200-1stgen-606 OBJECT IDENTIFIER ::= { ac3200-1stgen 606 }

		
		-- 1.3.6.1.4.1.3715.11.3202
		ac3200-2ndgen OBJECT IDENTIFIER ::= { acx 3202 }

		
		-- 1.3.6.1.4.1.3715.11.3202.606
		ac3200-2ndgen-606 OBJECT IDENTIFIER ::= { ac3200-2ndgen 606 }

		
		-- 1.3.6.1.4.1.3715.11.3203
		ac3200-3rdgen OBJECT IDENTIFIER ::= { acx 3203 }

		
		-- 1.3.6.1.4.1.3715.11.3203.606
		ac3200-3rdgen-606 OBJECT IDENTIFIER ::= { ac3200-3rdgen 606 }

		
		-- 1.3.6.1.4.1.3715.11.3210
		ac3210 OBJECT IDENTIFIER ::= { acx 3210 }

		
		-- 1.3.6.1.4.1.3715.11.3210.1
		ac3210preSlope1GHz OBJECT-TYPE
			SYNTAX INTEGER
				{
				preSlopeFlat(1),
				preSloped(2)
				}
			ACCESS read-write
			STATUS mandatory
			DESCRIPTION
				"Forward path fixed 1.0 GHz preslope.
				
				Enumeration
				2: Enable 1.0 GHz preslope.
				1: Disable 1.0 GHz preslope."
			::= { ac3210 1 }

		
		-- 1.3.6.1.4.1.3715.11.3210.2
		ac3210trunkDistributionSelection OBJECT-TYPE
			SYNTAX INTEGER
				{
				flat(1),
				trunk(2)
				}
			ACCESS read-write
			STATUS mandatory
			DESCRIPTION
				"Distribution/flat vs. trunk selection.
				
				Enumeration
				2: Trunk.
				1: Distribution/flat."
			::= { ac3210 2 }

		
		-- 1.3.6.1.4.1.3715.11.3210.3
		ac3210inputBypassOutput3Selection OBJECT-TYPE
			SYNTAX INTEGER
				{
				inputBypass(1),
				output3(2),
				forcedInputBypass(3),
				forcedOutput3(4),
				other(5),
				unknown(6),
				notAvailable(7)
				}
			ACCESS read-write
			STATUS mandatory
			DESCRIPTION
				"Port 3 mode selection.
				
				Enumeration
				1: input bypass, 
				2: output 3, 
				3: forced input bypass, 
				4: forced output 3, 
				5: other, 
				6: unknown, 
				7: N/A"
			::= { ac3210 3 }

		
		-- 1.3.6.1.4.1.3715.11.3210.4
		ac3210irpc OBJECT-TYPE
			SYNTAX INTEGER
				{
				ac3210irpcEnabled(1),
				ac3210irpcDisabled(2)
				}
			ACCESS read-write
			STATUS mandatory
			DESCRIPTION
				"Intelligent return path level and slope control. 
				iRPC: intelligent Return Path Control.
				
				1: Enabled
				2: Disabled"
			::= { ac3210 4 }

		
		-- 1.3.6.1.4.1.3715.11.3210.3210
		ac3210-generations OBJECT IDENTIFIER ::= { ac3210 3210 }

		
		-- 1.3.6.1.4.1.3715.11.3210.3210.1
		ac3210-1stgen OBJECT IDENTIFIER ::= { ac3210-generations 1 }

		
		-- 1.3.6.1.4.1.3715.11.3210.3210.2
		ac3210-2ndgen OBJECT IDENTIFIER ::= { ac3210-generations 2 }

		
		-- 1.3.6.1.4.1.3715.11.3210.3210.3
		ac3210-3rdgen OBJECT IDENTIFIER ::= { ac3210-generations 3 }

		
		-- 1.3.6.1.4.1.3715.11.3280
		ac3280 OBJECT IDENTIFIER ::= { acx 3280 }

		
		-- 1.3.6.1.4.1.3715.11.3280.3280
		ac3280-generations OBJECT IDENTIFIER ::= { ac3280 3280 }

		
		-- 1.3.6.1.4.1.3715.11.3280.3280.1
		ac3280-1stgen OBJECT IDENTIFIER ::= { ac3280-generations 1 }

		
		-- 1.3.6.1.4.1.3715.11.8000
		ac8000 OBJECT IDENTIFIER ::= { acx 8000 }

		
		-- 1.3.6.1.4.1.3715.11.8001
		ac8000i OBJECT IDENTIFIER ::= { acx 8001 }

		
		-- 1.3.6.1.4.1.3715.11.8700
		ac8700 OBJECT IDENTIFIER ::= { acx 8700 }

		
		-- 1.3.6.1.4.1.3715.11.8710
		ac8710 OBJECT IDENTIFIER ::= { acx 8710 }

		
		-- 1.3.6.1.4.1.3715.11.8710.1
		ac8710-generations OBJECT IDENTIFIER ::= { ac8710 1 }

		
		-- 1.3.6.1.4.1.3715.11.8710.1.1
		ac8710-1stgen OBJECT IDENTIFIER ::= { ac8710-generations 1 }

		
		-- 1.3.6.1.4.1.3715.11.8710.1.2
		ac8710-2ndgen OBJECT IDENTIFIER ::= { ac8710-generations 2 }

		
		-- 1.3.6.1.4.1.3715.11.8800
		ac8800 OBJECT IDENTIFIER ::= { acx 8800 }

		
		-- 1.3.6.1.4.1.3715.11.8810
		ac8810 OBJECT IDENTIFIER ::= { acx 8810 }

		
		-- 1.3.6.1.4.1.3715.11.8810.1
		ac8810-generations OBJECT IDENTIFIER ::= { ac8810 1 }

		
		-- 1.3.6.1.4.1.3715.11.8810.1.1
		ac8810-1stgen OBJECT IDENTIFIER ::= { ac8810-generations 1 }

		
		-- 1.3.6.1.4.1.3715.11.8810.1.2
		ac8810-2ndgen OBJECT IDENTIFIER ::= { ac8810-generations 2 }

		
		-- 1.3.6.1.4.1.3715.11.9000
		ac9000 OBJECT IDENTIFIER ::= { acx 9000 }

		
		-- 1.3.6.1.4.1.3715.11.9001
		ac9000-2ndgen OBJECT IDENTIFIER ::= { acx 9001 }

		
		-- 1.3.6.1.4.1.3715.11.9100
		ac9100 OBJECT IDENTIFIER ::= { acx 9100 }

		
		-- 1.3.6.1.4.1.3715.11.9100.1
		ac9100alc3FollowsAlc1 OBJECT-TYPE
			SYNTAX INTEGER
				{
				alc3FollowsAlc1Enabled(1),
				alc3FollowsAlc1Disabled(2)
				}
			ACCESS read-write
			STATUS mandatory
			DESCRIPTION
				"AC9100, AC9100 NEO and AC9400 only.
				
				ALC special mode when ALC enabled: ALC 3 follows ALC 1. Only ALC 1 pilots are used. ALC 3 pilots are recommended to disable (set frequency to 0 MHz)."
			::= { ac9100 1 }

		
		-- 1.3.6.1.4.1.3715.11.9100.2
		ac9100NEO OBJECT IDENTIFIER ::= { ac9100 2 }

		
		-- 1.3.6.1.4.1.3715.11.9100.2.1
		ac9100neoReturnPathRfSplit OBJECT-TYPE
			SYNTAX INTEGER
				{
				returnPathSplitNone(0),
				returnPathSplitTx2toTx1(16),
				returnPathSplitTx4toTx3(16384),
				returnPathSplitTx2toTx1andTx4toTx3(16400)
				}
			ACCESS read-write
			STATUS mandatory
			DESCRIPTION
				"Return path RF split.
				
				Uint16 splitter to four bit groups 0xDCBA, where group is source (split from) A: Tx1, B: Tx2: C: Tx3, D: Tx4 
				and each bit group has bitmask of destination transmitters (split to) 0bklmn, where k: Tx4, l: Tx3, m: Tx2, n: Tx1. 
				Bit 0: not active/no split, bit 1: active/splitted.
				
				Example: Split Tx2 signal to Tx1: 0x0010. Example2: Split Tx4 signal to Tx3: 0x4000.
				
				Currently supported only four different combinationts.
				- No splits (0)
				- Split Tx2 to Tx1 (16)
				- Split Tx4 to Tx3 (16384)
				- Split Tx2 to Tx1 and Tx4 to Tx3 (16400)"
			::= { ac9100NEO 1 }

		
		-- 1.3.6.1.4.1.3715.11.9100.3
		ac9100alc3OffsetToAlc1 OBJECT-TYPE
			SYNTAX INTEGER
			ACCESS read-write
			STATUS mandatory
			DESCRIPTION
				"AC9100, AC9100 NEO and AC9400 only.
				
				Output3 offset. Unit 0.01 dB.
				
				When ac9100alc3FollowsAlc1 and ALC is enabled, then output 3 gain is ouput 1 gain + ac9100alc3OffsetToAlc1."
			::= { ac9100 3 }

		
		-- 1.3.6.1.4.1.3715.11.9400
		ac9400 OBJECT IDENTIFIER ::= { acx 9400 }

		
		-- 1.3.6.1.4.1.3715.11.9400.1
		ac9400-generations OBJECT IDENTIFIER ::= { ac9400 1 }

		
		-- 1.3.6.1.4.1.3715.11.9400.1.1
		ac9400-1stgen OBJECT IDENTIFIER ::= { ac9400-generations 1 }

		
		-- 1.3.6.1.4.1.3715.11.9400.2
		ac9400output12ModuleType OBJECT-TYPE
			SYNTAX INTEGER
				{
				outputModuleShort(1),
				outputModuleAC6124v1(2),
				outputModuleAC6124v2(3),
				outputModuleAC6113(4),
				outputModuleAC6114(5),
				outputModuleAC6115(6),
				outputModuleAC6117(7),
				outputModuleAC6120(12),
				outputModuleOpen(13),
				outputModuleReserved(14),
				outputModuleUnknown(15),
				outputModuleNA(16)
				}
			ACCESS read-only
			STATUS mandatory
			DESCRIPTION
				"Output 1+2 output module type.
				 1: short
				 2: AC6124v1 (unknown module)
				 3: AC6124v2
				 4: AC6113
				 5: AC6114
				 6: AC6115
				 7: AC6117
				12: AC6120
				13: open
				14: reserved
				15: unknown
				16: N/A"
			::= { ac9400 2 }

		
		-- 1.3.6.1.4.1.3715.11.9400.3
		ac9400output34ModuleType OBJECT-TYPE
			SYNTAX INTEGER
				{
				outputModuleShort(1),
				outputModuleAC6124v1(2),
				outputModuleAC6124v2(3),
				outputModuleAC6113(4),
				outputModuleAC6114(5),
				outputModuleAC6115(6),
				outputModuleAC6117(7),
				outputModuleAC6120(12),
				outputModuleOpen(13),
				outputModuleReserved(14),
				outputModuleUnknown(15),
				outputModuleNA(16)
				}
			ACCESS read-only
			STATUS mandatory
			DESCRIPTION
				"Output 3+4 output module type.
				 1: short
				 2: AC6124v1 (unknown module)
				 3: AC6124v2
				 4: AC6113
				 5: AC6114
				 6: AC6115
				 7: AC6117
				12: AC6120
				13: open
				14: reserved
				15: unknown
				16: N/A"
			::= { ac9400 3 }

		
		-- 1.3.6.1.4.1.3715.11.9400.4
		ac9400rpInputToOptTxSlotMapping OBJECT-TYPE
			SYNTAX INTEGER
			ACCESS read-only
			STATUS mandatory
			DESCRIPTION
				"Node return path RF input port -> optical transmitter slot # mapping. 
				xxxx yyyy zzzz wwww, where x=TxSlot 4…w=TxSlot1 and bits/nibble: dcba: d: RP input 1, c: RP input 3, b: RP input 2, a: RP input 1
				
				Examples
				RP input 2 to TxSlot 2: 0x0020
				RP input 1 and 3 to TxSlot 2 and 4: 0x5050
				"
			::= { ac9400 4 }

		
	
--
-- Trap definitions
--
	
		functionsDisabled TRAP-TYPE 
			ENTERPRISE acx
			VARIABLES { acxTransponderFunctionStatus }
			DESCRIPTION 
				"A notification that the functions are not running, which
				may mean that the programmable alarms are disabled.
				
				Possible reasons for the functions not running are:
				- the configuration is incompatible with the
				  programmed, or expected configuration
				- a hardware failure has occurred
				- a valid function set is not downloaded
				"
			::=  1

	
	END

--
-- TELESTE-ACX-MIB.mib
--
