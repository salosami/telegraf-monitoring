--
-- TELESTE-FUNCTIONAL-MODULE-MIB.mib
-- MIB generated by MG-SOFT Visual MIB Builder 2021 (64-bit) Version 15.00  Build 1510
-- Monday, September 27, 2021 at 10:46:11
--

-- ****************************************************************************
-- Copyright (c) 2003-2014 by:
-- 
-- Teleste Corporation
-- Seponkatu 1
-- FIN-20660 Littoinen, Finland
-- tel. +358 2 2605 611
-- url: http://www.teleste.com
-- 
-- Module Name:   TELESTE-FUNCTIONAL-MODULE-MIB
-- 
-- Description:   MIB module describing Teleste functional module interface specific objects
-- 
-- Revision history:
-- -----------------
-- 4, 27.9.2021, Sami Kuusisto
-- - Added moduleInternalErrorUnknownModule.
-- 
-- 3, 24.9.2014, Sami Kuusisto
-- - Added enumeration modulePoweringReserved(2) to modulePowering.
-- - Added "Powered from USB" description to moduleStatus: statusReserved(4).
-- 
-- 2, 18.3.2014, Sami Kuusisto
-- - Added moduleInfoTable
-- 
-- 1, 10.3.2014, Sami Kuusisto
-- - Initial version.
-- 
-- ****************************************************************************
-- 

	TELESTE-FUNCTIONAL-MODULE-MIB DEFINITIONS ::= BEGIN
 
		IMPORTS
			OBJECT-TYPE			
				FROM RFC-1212			
			functional			
				FROM TELESTE-ROOT-MIB;
	
	
	
--
-- Node definitions
--
	
		-- 1.3.6.1.4.1.3715.100.99
		functionalModule OBJECT IDENTIFIER ::= { functional 99 }

		
		-- 1.3.6.1.4.1.3715.100.99.1
		functionalModuleTable OBJECT-TYPE
			SYNTAX SEQUENCE OF FunctionalModuleEntry
			ACCESS not-accessible
			STATUS mandatory
			DESCRIPTION
				"Table of functional modules/interfaces. They might be related to physical modules or they might nt be."
			::= { functionalModule 1 }

		
		-- 1.3.6.1.4.1.3715.100.99.1.1
		functionalModuleEntry OBJECT-TYPE
			SYNTAX FunctionalModuleEntry
			ACCESS not-accessible
			STATUS mandatory
			INDEX { functionalModuleId }
			::= { functionalModuleTable 1 }

		
		FunctionalModuleEntry ::=
			SEQUENCE { 
				functionalModuleId
					INTEGER,
				functionalModuleName
					OCTET STRING
			 }

		-- 1.3.6.1.4.1.3715.100.99.1.1.1
		functionalModuleId OBJECT-TYPE
			SYNTAX INTEGER (1..65535)
			ACCESS read-write
			STATUS mandatory
			DESCRIPTION
				"RW index, because SNMP v1 doesn't support not-accessible.
				"
			::= { functionalModuleEntry 1 }

		
		-- 1.3.6.1.4.1.3715.100.99.1.1.2
		functionalModuleName OBJECT-TYPE
			SYNTAX OCTET STRING
			ACCESS read-only
			STATUS mandatory
			DESCRIPTION
				"Human readable module name."
			::= { functionalModuleEntry 2 }

		
		-- 1.3.6.1.4.1.3715.100.99.2
		moduleInfoTable OBJECT-TYPE
			SYNTAX SEQUENCE OF ModuleInfoEntry
			ACCESS not-accessible
			STATUS mandatory
			::= { functionalModule 2 }

		
-- Status of module.
-- 
		-- 1.3.6.1.4.1.3715.100.99.2.1
		moduleInfoEntry OBJECT-TYPE
			SYNTAX ModuleInfoEntry
			ACCESS not-accessible
			STATUS mandatory
			INDEX { functionalModuleId }
			::= { moduleInfoTable 1 }

		
		ModuleInfoEntry ::=
			SEQUENCE { 
				moduleStatus
					INTEGER,
				modulePowering
					INTEGER,
				moduleInternalErrorUnknownModule
					INTEGER
			 }

		-- 1.3.6.1.4.1.3715.100.99.2.1.1
		moduleStatus OBJECT-TYPE
			SYNTAX INTEGER
				{
				statusOk(1),
				statusUnknownModule(2),
				statusInternalError(3),
				statusReserved(4),
				statusUnknown(5),
				statusNA(6),
				statusOther(7)
				}
			ACCESS read-only
			STATUS mandatory
			DESCRIPTION
				"1: Module status ok
				2: Unknown module/plugin detected.
				3: Internal error
				4: Reserved for compatibility reasons (Powered from USB). Do not use.
				5: Status unknown
				6: Status information unavailable
				7: Status other"
			::= { moduleInfoEntry 1 }

		
		-- 1.3.6.1.4.1.3715.100.99.2.1.2
		modulePowering OBJECT-TYPE
			SYNTAX INTEGER
				{
				modulePoweringNormal(1),
				modulePoweringReserved(2),
				modulePoweringError(3),
				modulePoweringUSB(4),
				modulePoweringUnknown(5),
				modulePoweringNA(6),
				modulePoweringOther(7)
				}
			ACCESS read-only
			STATUS mandatory
			DESCRIPTION
				"Module powering status
				1: Normal/Full power
				2: reserved for compability reasons
				3: Powering error
				4: USB powered
				5: Powering state unknown
				6: Powering state unavailable
				7: Powering state other"
			::= { moduleInfoEntry 2 }

		
		-- 1.3.6.1.4.1.3715.100.99.2.1.3
		moduleInternalErrorUnknownModule OBJECT-TYPE
			SYNTAX INTEGER
			ACCESS read-only
			STATUS mandatory
			DESCRIPTION
				"Internal error and unknown module causes bitmasks.
				
				Internal error: I2C				0x00000001
				Internal error: BAD ID AREA			0x00000002
				Internal error: EEPROM INITIALIZATION		0x00000004
				Internal error: SLIP LINK OR CM PROBLEM		0x00000008
				Internal error: DEFAULT STATION DRIVER		0x04000000
				Internal error: EXT FLASH			0x08000000
				Internal error: PLL NOT LOCKING			0x10000000
					
				Unknown module:  PLUGINS MISMATCH		0x00000010
				Unknown module:  FP PLUGIN MODULE 1		0x00000020
				Unknown module:  FP PLUGIN MODULE 2		0x00000040
				Unknown module:  RP PLUGIN MODULE 1		0x00000080
				Unknown module:  RP PLUGIN MODULE 2		0x00000100
				Unknown module:  FP UNIVERSAL PLUGIN MODULE 1	0x00000200
				Unknown module:  FP UNIVERSAL PLUGIN MODULE 2	0x00000400
				Unknown module:  RP UNIVERSAL PLUGIN MODULE 1	0x00000800
				Unknown module:  RP UNIVERSAL PLUGIN MODULE 2	0x00001000
				Unknown module:  TRANSPONDER			0x00002000
				Unknown module:  DIPLEX FILTER 1		0x00004000
				Unknown module:  DIPLEX FILTER 2		0x00008000
				Unknown module:  DIPLEX FILTER 3		0x00010000
				Unknown module:  DIPLEX FILTER 4		0x00020000
				Unknown module:  TRANSMITTER 1			0x00040000
				Unknown module:  TRANSMITTER 2			0x00080000
				Unknown module:  TRANSMITTER 3			0x00100000
				Unknown module:  TRANSMITTER 4			0x00200000
				Unknown module:  RECEIVER 1			0x00400000
				Unknown module:  RECEIVER 2			0x00800000
				Unknown module:  RECEIVER 3			0x01000000
				Unknown module:  RECEIVER 4			0x02000000
				Unknown module:  INPUT MODULE			0x20000000
				Unknown module:  OUTPUT MODULE			0x40000000
				"
			::= { moduleInfoEntry 3 }

		
	
	END

--
-- TELESTE-FUNCTIONAL-MODULE-MIB.mib
--
