--
-- TELESTE-HDOEDFA2-MIB.mib
-- MIB generated by MG-SOFT Visual MIB Builder Version 4.0 Build 349
-- Thursday, December 17, 2009 at 10:10:58
--

-- ****************************************************************************
-- Copyright (c) 2005-2009 by:
-- 
-- Teleste Corporation
-- Seponkatu 1
-- FIN-20660 Littoinen, Finland
-- tel. +358 2 2605 611
-- url: http://www.teleste.com
-- 
-- Module Name:   TELESTE-HDOEDFA2-MIB
-- 
-- Description:   MIB module describing HDO EDFA2 objects
-- 
-- Revision History:
-- -----------------
-- 1.0 17.12.2009 Rainer Salminen and Sami Salo
-- 
-- 
-- ****************************************************************************
-- 

	TELESTE-HDOEDFA2-MIB DEFINITIONS ::= BEGIN
 
		IMPORTS
			OBJECT-TYPE			
				FROM RFC-1212			
			Counter			
				FROM RFC1155-SMI			
			sysUpTime, DisplayString			
				FROM RFC1213-MIB			
			oemodules			
				FROM TELESTE-HDO-MIB;
	
	
	
--
-- Node definitions
--
	
-- EDFA2 node definitions
		-- 1.3.6.1.4.1.3715.14.2.103
		edfa2 OBJECT IDENTIFIER ::= { oemodules 103 }

		
		-- 1.3.6.1.4.1.3715.14.2.103.1
		edfaCommon OBJECT IDENTIFIER ::= { edfa2 1 }

		
		-- 1.3.6.1.4.1.3715.14.2.103.1.1
		commonVendor OBJECT-TYPE
			SYNTAX DisplayString (SIZE (0..255))
			ACCESS read-only
			STATUS mandatory
			DESCRIPTION
				"Manufacturer of the device."
			::= { edfaCommon 1 }

		
		-- 1.3.6.1.4.1.3715.14.2.103.1.2
		commonModelName OBJECT-TYPE
			SYNTAX DisplayString (SIZE (0..255))
			ACCESS read-only
			STATUS mandatory
			DESCRIPTION
				"Model number of the device."
			::= { edfaCommon 2 }

		
		-- 1.3.6.1.4.1.3715.14.2.103.1.3
		commonSerialNumber OBJECT-TYPE
			SYNTAX DisplayString (SIZE (0..15))
			ACCESS read-only
			STATUS mandatory
			DESCRIPTION
				"Serial number of the device."
			::= { edfaCommon 3 }

		
		-- 1.3.6.1.4.1.3715.14.2.103.1.4
		commonManufacturingDate OBJECT-TYPE
			SYNTAX DisplayString (SIZE (10))
			ACCESS read-only
			STATUS mandatory
			DESCRIPTION
				"Manufacturing date of the device."
			::= { edfaCommon 4 }

		
		-- 1.3.6.1.4.1.3715.14.2.103.1.5
		commonFirmwareVersion OBJECT-TYPE
			SYNTAX DisplayString (SIZE (0..255))
			ACCESS read-only
			STATUS mandatory
			DESCRIPTION
				"Firmware version of the device."
			::= { edfaCommon 5 }

		
		-- 1.3.6.1.4.1.3715.14.2.103.1.6
		commonTotalUpTime OBJECT-TYPE
			SYNTAX Counter
			ACCESS read-only
			STATUS mandatory
			DESCRIPTION
				"Total operating time of the device. Unit 1 day"
			::= { edfaCommon 6 }

		
		-- 1.3.6.1.4.1.3715.14.2.103.1.7
		commonTamperStatus OBJECT-TYPE
			SYNTAX INTEGER
				{
				intact(1),
				compromised(2)
				}
			ACCESS read-only
			STATUS mandatory
			DESCRIPTION
				"Status of the tamper switch."
			::= { edfaCommon 7 }

		
	
	END

--
-- TELESTE-HDOEDFA2-MIB.mib
--
