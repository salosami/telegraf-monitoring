TELESTE-FTTX-ROOT-MIB DEFINITIONS ::= BEGIN

IMPORTS
   ftth
      FROM TELESTE-ROOT-MIB;

-- v1.0	2008-10-20	salmra
-- v1.1	2008-10-20	salmra : moved t4 to TELESTE-T4-MIB

gateway           OBJECT IDENTIFIER ::= { ftth 1 }
switch            OBJECT IDENTIFIER ::= { ftth 2 }

admin             OBJECT IDENTIFIER ::= { ftth 100 }

END
