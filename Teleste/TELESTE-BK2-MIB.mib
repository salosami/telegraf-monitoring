--
-- TELESTE-BK2-MIB.mib
-- MIB generated by MG-SOFT Visual MIB Builder 2013 (64-bit) Version 9.0  Build 760
-- Tuesday, May 24, 2016 at 09:00:37
--

-- ****************************************************************************
-- Copyright (c) 2000-2015 by:
-- 
-- Teleste Corporation
-- Telestenkatu 1
-- FI-20660 Littoinen, Finland
-- tel. +358 2 2605 611
-- url: http://www.teleste.com
-- 
-- Description: Optical and headend BK module definitions
-- 
-- Revision History:
-- -----------------
-- 43, 24.5.2016, Sami Halen
-- - added objects for 2 new RF detectors to kplTable
-- 
-- 42, 12.8.2015, Sami Halen
-- - changed kplDetOffset & related alarm limits' unit from dBµV to dB
-- 
-- 41, 25.6.2015, Matti Susi
-- - added value ranges to kplTable gain and slope objects
-- 
-- 40, 22.4.2015, Sami Halen
-- - added kplTable, copied from eVrTable
-- - removed kplGainMode from kplTable
-- - removed eVrGainS1/2/3/4 and eVrSlopeS1/2/3/4 from eVrTable
-- - removed references to BKK421 from eVrTable
-- 
-- kplTable
-- 39, 25.3.2015, Matti Susi
-- - added BKK421 port allocations to eVrTable
-- 
-- 38, 22.1.2015, Sami Kuusisto
-- - added 5: N/A to eVrGainMode
-- 
-- 37, 17.11.2014, Sami Halen
-- - added eVrGainS1/2/3/4 and eVrSlopeS1/2/3/4 to eVrTable
-- 
-- 1.36, 28.4.2014, Sami Kuusisto and Rainer Salminen
-- - combined oVTx2LaserFrequencyNominalHigh and oVTx2LaserFrequencyNominalLow to oVTx2LaserFrequencyNominal.
-- - combined oVTx2LaserFrequencyOffsetHigh and oVTx2LaserFrequencyOffsetLow to oVTx2LaserFrequencyOffset.
-- - renamed oVTx2FiberType to oVTx2SbsFiberType.
-- - renamed oVTx2FiberLength to oVTx2SbsFiberLength.
-- - renamed oVTx2FibreLength to oVTx2FiberLength.
-- - renumbered childs.
-- 
-- 1.35, 4.4.2014, Sami Kuusisto and Rainer Salminen
-- - updates to oVTx2Table
-- 
-- 1.34, 3.4.2014, Sami Kuusisto and Rainer Salminen
-- - updates to oVTx2Table status parameter enumerations.
-- 
-- 1.33, 2.4.2014, Sami Kuusisto and Rainer Salminen
-- - updates to oVTx2Table.
-- 
-- 1.32, 1.4.2014, Sami Kuusisto and Rainer Salminen
-- - added oVTx2Table.
-- 
-- 1.31, 24.10.2013 Matti Susi
-- - added objects for power and gain label and unit
-- 
-- 1.30, 11.9.2013 Matti Susi
-- - clarified oVA2 object descriptions to higlight power/gain mode differences
-- 
-- 1.29, 12.11.2012, Sami Halen/Matti Susi
-- - added/corrected BKT825 values to eVrGainMode
-- - editorial: changed all "optional" statuses to "mandatory"
-- 
-- 1.28,13.9.2012 Matti Susi
-- - added OVA2 section
-- 
-- 1.27, 3.7.2012 Sami Halen
-- - added BKT825 values to eVrGainMode
-- 
-- 1.26, 27.5.2011 Matti Susi
-- - added NC gain object for oTxD
-- 
-- 1.25, 15.10.2008 Matti Susi
-- - added objects for BOR300
-- 
-- 1.24, 18.9.2006 Matti Susi
-- - added three new objects for OVA2
-- - changed some OVA object names for better consistency
-- 
-- 1.23, 30.3.2005 Matti Susi
-- - inserted oTxD section
-- 
-- 1.22, 13.5.2003 Matti Susi
-- - oVA status objects corrected and reorganised
-- 
-- 1.21, 11.3.2003 Matti Susi
-- - hVr changed to eVr
-- 
-- 1.2, 7.3.2003 Matti Susi
-- - table and object names harmonised with BK-OptiFlex family 
-- 
-- 1.1, 14.1.2003 Matti Susi
-- - range definitions added
-- - unit definitions corrected
-- 
-- 1.0, 20.12.2002 Matti Susi
-- - Initial official version
-- 
-- ****************************************************************************

	TELESTE-BK2-MIB DEFINITIONS ::= BEGIN
 
		IMPORTS
			OBJECT-TYPE			
				FROM RFC-1212			
			moduleId			
				FROM TELESTE-COMMON-MIB			
			bk			
				FROM TELESTE-ROOT-MIB;
	
	
--
-- Node definitions
--
	
		-- 1.3.6.1.4.1.3715.3.4
		bkModules2 OBJECT IDENTIFIER ::= { bk 4 }

		
		-- 1.3.6.1.4.1.3715.3.4.14
		eVrTable OBJECT-TYPE
			SYNTAX SEQUENCE OF EVrEntry
			ACCESS not-accessible
			STATUS mandatory
			DESCRIPTION
				"This table contains element specific information
				for H Amplifier (BKT824/5) modules inserted into
				the BK backplane."
			::= { bkModules2 14 }

		
		-- 1.3.6.1.4.1.3715.3.4.14.1
		eVrEntry OBJECT-TYPE
			SYNTAX EVrEntry
			ACCESS not-accessible
			STATUS mandatory
			DESCRIPTION
				"Row in Table. Note that index is moduleIndex which is column in 
				the moduleTable defined in TELESTE-COMMON-MIB. Rows in this table
				exist only if there are corresponding rows in the moduleTable."
			INDEX { moduleId }
			::= { eVrTable 1 }

		
		EVrEntry ::=
			SEQUENCE { 
				eVrGain
					INTEGER,
				eVrSlope
					INTEGER,
				eVrDetOffset
					INTEGER,
				eVrDetRefMode
					INTEGER,
				eVrDetRefValue
					INTEGER,
				eVrDetOffsetHiHi
					INTEGER,
				eVrDetOffsetHi
					INTEGER,
				eVrDetOffsetLo
					INTEGER,
				eVrDetOffsetLoLo
					INTEGER,
				eVrDetOffsetDeadband
					INTEGER,
				eVrDetAverageMode
					INTEGER,
				eVrGainMode
					INTEGER,
				eVrRfLevelStatus
					INTEGER,
				eVrTemperatureStatus
					INTEGER
			 }

		-- 1.3.6.1.4.1.3715.3.4.14.1.1
		eVrGain OBJECT-TYPE
			SYNTAX INTEGER
			ACCESS read-write
			STATUS mandatory
			DESCRIPTION
				"Gain control value (main input).
				Unit 0.01 dB."
			::= { eVrEntry 1 }

		
		-- 1.3.6.1.4.1.3715.3.4.14.1.2
		eVrSlope OBJECT-TYPE
			SYNTAX INTEGER
			ACCESS read-write
			STATUS mandatory
			DESCRIPTION
				"Slope control value (main input).
				Unit 0.01 dB.
				"
			::= { eVrEntry 2 }

		
		-- 1.3.6.1.4.1.3715.3.4.14.1.3
		eVrDetOffset OBJECT-TYPE
			SYNTAX INTEGER (-10000..10000)
			ACCESS read-only
			STATUS mandatory
			DESCRIPTION
				"Broadband detector offset value. Unit 0.01 dBµV."
			::= { eVrEntry 3 }

		
		-- 1.3.6.1.4.1.3715.3.4.14.1.4
		eVrDetRefMode OBJECT-TYPE
			SYNTAX INTEGER
				{
				refFactory(1),
				refUser(2)
				}
			ACCESS read-write
			STATUS mandatory
			DESCRIPTION
				"Current reference mode.
				1 = factory
				2 = user"
			::= { eVrEntry 4 }

		
		-- 1.3.6.1.4.1.3715.3.4.14.1.5
		eVrDetRefValue OBJECT-TYPE
			SYNTAX INTEGER
			ACCESS read-write
			STATUS mandatory
			DESCRIPTION
				"Nominal detector value. Unit 0.01 dBµV."
			::= { eVrEntry 5 }

		
		-- 1.3.6.1.4.1.3715.3.4.14.1.6
		eVrDetOffsetHiHi OBJECT-TYPE
			SYNTAX INTEGER (0..10000)
			ACCESS read-write
			STATUS mandatory
			DESCRIPTION
				"Broadband detector HIGH ALARM limit. Unit 0.01 dBµV."
			::= { eVrEntry 6 }

		
		-- 1.3.6.1.4.1.3715.3.4.14.1.7
		eVrDetOffsetHi OBJECT-TYPE
			SYNTAX INTEGER (0..10000)
			ACCESS read-write
			STATUS mandatory
			DESCRIPTION
				"Broadband detector HIGH WARNING limit. Unit 0.01 dBµV."
			::= { eVrEntry 7 }

		
		-- 1.3.6.1.4.1.3715.3.4.14.1.8
		eVrDetOffsetLo OBJECT-TYPE
			SYNTAX INTEGER (-10000..0)
			ACCESS read-write
			STATUS mandatory
			DESCRIPTION
				"Broadband detector LOW WARNING limit. Unit 0.01 dBµV."
			::= { eVrEntry 8 }

		
		-- 1.3.6.1.4.1.3715.3.4.14.1.9
		eVrDetOffsetLoLo OBJECT-TYPE
			SYNTAX INTEGER (-10000..0)
			ACCESS read-write
			STATUS mandatory
			DESCRIPTION
				"Broadband detector LOW ALARM limit. Unit 0.01 dBµV."
			::= { eVrEntry 9 }

		
		-- 1.3.6.1.4.1.3715.3.4.14.1.10
		eVrDetOffsetDeadband OBJECT-TYPE
			SYNTAX INTEGER (50..1000)
			ACCESS read-write
			STATUS mandatory
			DESCRIPTION
				"Broadband detector deadband value. Unit 0.01 dBµV."
			::= { eVrEntry 10 }

		
		-- 1.3.6.1.4.1.3715.3.4.14.1.11
		eVrDetAverageMode OBJECT-TYPE
			SYNTAX INTEGER
				{
				modeOff(1),
				modeOn(2)
				}
			ACCESS read-write
			STATUS mandatory
			DESCRIPTION
				"Broadband detector's averaging status:
				1 = averaging off
				2 = averaging on"
			::= { eVrEntry 11 }

		
		-- 1.3.6.1.4.1.3715.3.4.14.1.12
		eVrGainMode OBJECT-TYPE
			SYNTAX INTEGER
				{
				gain14dB(1),
				gain24dB(2),
				gain15dB(3),
				gain25dB(4),
				gainNA(5)
				}
			ACCESS read-write
			STATUS mandatory
			DESCRIPTION
				"Amplifier gain setting:
				1 = 14 dB (BKT824)
				2 = 24 dB (BKT824)
				3 = 15 dB (BKT825)
				4 = 25 dB (BKT825)
				5 = N/A: Amplifier gain setting not available
				
				At lower gain value the input amplifier is switched
				off and by-passed to reduce power consumption."
			::= { eVrEntry 12 }

		
		-- 1.3.6.1.4.1.3715.3.4.14.1.13
		eVrRfLevelStatus OBJECT-TYPE
			SYNTAX INTEGER
				{
				levelNormal(1),
				levelHIHI(2),
				levelHI(3),
				levelLO(4),
				levelLOLO(5)
				}
			ACCESS read-only
			STATUS mandatory
			DESCRIPTION
				"RF level status
				1 = OK
				2 = HIHI
				3 = HI
				4 = LO
				5 = LOLO"
			::= { eVrEntry 13 }

		
		-- 1.3.6.1.4.1.3715.3.4.14.1.14
		eVrTemperatureStatus OBJECT-TYPE
			SYNTAX INTEGER
				{
				tempNormal(1),
				tempHIHI(2),
				tempHI(3),
				tempLO(4),
				tempLOLO(5)
				}
			ACCESS read-only
			STATUS mandatory
			DESCRIPTION
				"Module temperature Status.
				1 = OK
				2 = HIHI
				3 = HI
				4 = LO
				5 = LOLO"
			::= { eVrEntry 14 }

		
		-- 1.3.6.1.4.1.3715.3.4.23
		oPSTable OBJECT-TYPE
			SYNTAX SEQUENCE OF OPSEntry
			ACCESS not-accessible
			STATUS mandatory
			DESCRIPTION
				"This tablecontains element specific information
				for Optical Switch (BOS21X) modules inserted into
				the BK backplane."
			::= { bkModules2 23 }

		
		-- 1.3.6.1.4.1.3715.3.4.23.1
		oPSEntry OBJECT-TYPE
			SYNTAX OPSEntry
			ACCESS not-accessible
			STATUS mandatory
			DESCRIPTION
				"Row in Table. Note that index is moduleIndex which is column in 
				the moduleTable defined in TELESTE-COMMON-MIB. Rows in this table
				exist only if there are corresponding rows in the moduleTable."
			INDEX { moduleId }
			::= { oPSTable 1 }

		
		OPSEntry ::=
			SEQUENCE { 
				oPSInputPowerMain
					INTEGER,
				oPSInputPowerRes
					INTEGER,
				oPSInputPowerHiHiM
					INTEGER,
				oPSInputPowerHiM
					INTEGER,
				oPSInputPowerLoM
					INTEGER,
				oPSInputPowerLoLoM
					INTEGER,
				oPSInputPowerDeadbandM
					INTEGER,
				oPSInputPowerHiHiR
					INTEGER,
				oPSInputPowerHiR
					INTEGER,
				oPSInputPowerLoR
					INTEGER,
				oPSInputPowerLoLoR
					INTEGER,
				oPSInputPowerDeadbandR
					INTEGER,
				oPSMode
					INTEGER,
				oPSFallbackWaittime
					INTEGER,
				oPSRfDetectionMode
					INTEGER,
				oPSInputPowerMainStatus
					INTEGER,
				oPSInputPowerResStatus
					INTEGER,
				oPSRfLevelStatusMain
					INTEGER,
				oPSRfLevelStatusRes
					INTEGER,
				oPSActiveInput
					INTEGER
			 }

		-- 1.3.6.1.4.1.3715.3.4.23.1.1
		oPSInputPowerMain OBJECT-TYPE
			SYNTAX INTEGER (-600..1000)
			ACCESS read-only
			STATUS mandatory
			DESCRIPTION
				"Main channel optical input power (Range: -6.0...+10.0 dBm)
				Unit 0.01 dBm."
			::= { oPSEntry 1 }

		
		-- 1.3.6.1.4.1.3715.3.4.23.1.2
		oPSInputPowerRes OBJECT-TYPE
			SYNTAX INTEGER (-600..1000)
			ACCESS read-only
			STATUS mandatory
			DESCRIPTION
				"Reserve channel optical input power (Range: -6.0...+10.0 dBm)
				Unit 0.01 dBm."
			::= { oPSEntry 2 }

		
		-- 1.3.6.1.4.1.3715.3.4.23.1.3
		oPSInputPowerHiHiM OBJECT-TYPE
			SYNTAX INTEGER (-600..1000)
			ACCESS read-write
			STATUS mandatory
			DESCRIPTION
				"Main channel optical input power HIGH alarm limit.
				Unit 0.01 dBm."
			::= { oPSEntry 3 }

		
		-- 1.3.6.1.4.1.3715.3.4.23.1.4
		oPSInputPowerHiM OBJECT-TYPE
			SYNTAX INTEGER (-600..1000)
			ACCESS read-write
			STATUS mandatory
			DESCRIPTION
				"Main channel optical input power HIGH warning limit.
				Unit 0.01 dBm."
			::= { oPSEntry 4 }

		
		-- 1.3.6.1.4.1.3715.3.4.23.1.5
		oPSInputPowerLoM OBJECT-TYPE
			SYNTAX INTEGER (-600..1000)
			ACCESS read-write
			STATUS mandatory
			DESCRIPTION
				"Main channel optical input power LOW warning limit.
				Unit 0.01 dBm."
			::= { oPSEntry 5 }

		
		-- 1.3.6.1.4.1.3715.3.4.23.1.6
		oPSInputPowerLoLoM OBJECT-TYPE
			SYNTAX INTEGER (-600..1000)
			ACCESS read-write
			STATUS mandatory
			DESCRIPTION
				"Main channel optical input power LOW alarm limit.
				Unit 0.01 dBm."
			::= { oPSEntry 6 }

		
		-- 1.3.6.1.4.1.3715.3.4.23.1.7
		oPSInputPowerDeadbandM OBJECT-TYPE
			SYNTAX INTEGER (50..500)
			ACCESS read-write
			STATUS mandatory
			DESCRIPTION
				"Main channel optical input power deadband value.
				Unit 0.01 dBm."
			::= { oPSEntry 7 }

		
		-- 1.3.6.1.4.1.3715.3.4.23.1.8
		oPSInputPowerHiHiR OBJECT-TYPE
			SYNTAX INTEGER (-600..1000)
			ACCESS read-write
			STATUS mandatory
			DESCRIPTION
				"Reserve channel optical input power HIGH alarm limit.
				Unit 0.01 dBm."
			::= { oPSEntry 8 }

		
		-- 1.3.6.1.4.1.3715.3.4.23.1.9
		oPSInputPowerHiR OBJECT-TYPE
			SYNTAX INTEGER (-600..1000)
			ACCESS read-write
			STATUS mandatory
			DESCRIPTION
				"Reserve channel optical input power HIGH warning limit.
				Unit 0.01 dBm."
			::= { oPSEntry 9 }

		
		-- 1.3.6.1.4.1.3715.3.4.23.1.10
		oPSInputPowerLoR OBJECT-TYPE
			SYNTAX INTEGER (-600..1000)
			ACCESS read-write
			STATUS mandatory
			DESCRIPTION
				"Reserve channel optical input power LOW warning limit.
				Unit 0.01 dBm."
			::= { oPSEntry 10 }

		
		-- 1.3.6.1.4.1.3715.3.4.23.1.11
		oPSInputPowerLoLoR OBJECT-TYPE
			SYNTAX INTEGER (-600..1000)
			ACCESS read-write
			STATUS mandatory
			DESCRIPTION
				"Reserve channel optical input power LOW alarm limit.
				Unit 0.01 dBm."
			::= { oPSEntry 11 }

		
		-- 1.3.6.1.4.1.3715.3.4.23.1.12
		oPSInputPowerDeadbandR OBJECT-TYPE
			SYNTAX INTEGER (50..500)
			ACCESS read-write
			STATUS mandatory
			DESCRIPTION
				"Reserve channel optical input power deadband value.
				Unit 0.01 dBm."
			::= { oPSEntry 12 }

		
		-- 1.3.6.1.4.1.3715.3.4.23.1.13
		oPSMode OBJECT-TYPE
			SYNTAX INTEGER
				{
				modeManual(1),
				modeRevertive(2),
				modeNonRevertive(3)
				}
			ACCESS read-write
			STATUS mandatory
			DESCRIPTION
				"1 Manual - The position of the optical switch is, independent of the 
				input signals, switched by the POSITION parameter.
				
				2 Revertive - The position of the optical switch automatically falls back
				from the reserve to the main channel, if the main channels
				signal is good during the fallback waittime.
				
				3 Non Revertive - The position of the optical switch stays in the reserve
				channel until the SWITCH_BACK parameter is written or the
				reserve channels signal fails."
			::= { oPSEntry 13 }

		
		-- 1.3.6.1.4.1.3715.3.4.23.1.14
		oPSFallbackWaittime OBJECT-TYPE
			SYNTAX INTEGER (30..300)
			ACCESS read-write
			STATUS mandatory
			DESCRIPTION
				"Waittime (30... 300sec) before switching back from the reserve to the main
				channel in revertive mode. Unit 1 second."
			::= { oPSEntry 14 }

		
		-- 1.3.6.1.4.1.3715.3.4.23.1.15
		oPSRfDetectionMode OBJECT-TYPE
			SYNTAX INTEGER
				{
				detectionOn(1),
				detectionOff(2)
				}
			ACCESS read-write
			STATUS mandatory
			DESCRIPTION
				"RF detection mode.
				1 = Enable RF detection
				2 = Disable RF detection"
			::= { oPSEntry 15 }

		
		-- 1.3.6.1.4.1.3715.3.4.23.1.16
		oPSInputPowerMainStatus OBJECT-TYPE
			SYNTAX INTEGER
				{
				powerNormal(1),
				powerHIHI(2),
				powerHI(3),
				powerLO(4),
				powerLOLO(5)
				}
			ACCESS read-only
			STATUS mandatory
			DESCRIPTION
				"Optical input power status
				1 = OK
				2 = HIHI
				3 = HI
				4 = LO
				5 = LOLO"
			::= { oPSEntry 16 }

		
		-- 1.3.6.1.4.1.3715.3.4.23.1.17
		oPSInputPowerResStatus OBJECT-TYPE
			SYNTAX INTEGER
				{
				powerNormal(1),
				powerHIHI(2),
				powerHI(3),
				powerLO(4),
				powerLOLO(5)
				}
			ACCESS read-only
			STATUS mandatory
			DESCRIPTION
				"Optical input power status
				1 = OK
				2 = HIHI
				3 = HI
				4 = LO
				5 = LOLO"
			::= { oPSEntry 17 }

		
		-- 1.3.6.1.4.1.3715.3.4.23.1.18
		oPSRfLevelStatusMain OBJECT-TYPE
			SYNTAX INTEGER
				{
				levelNormal(1),
				levelHIHI(2),
				levelHI(3),
				levelLO(4),
				levelLOLO(5)
				}
			ACCESS read-only
			STATUS mandatory
			DESCRIPTION
				"RF level status
				1 = OK
				2 = HIHI
				3 = HI
				4 = LO
				5 = LOLO"
			::= { oPSEntry 18 }

		
		-- 1.3.6.1.4.1.3715.3.4.23.1.19
		oPSRfLevelStatusRes OBJECT-TYPE
			SYNTAX INTEGER
				{
				levelNormal(1),
				levelHIHI(2),
				levelHI(3),
				levelLO(4),
				levelLOLO(5)
				}
			ACCESS read-only
			STATUS mandatory
			DESCRIPTION
				"RF level status
				1 = OK
				2 = HIHI
				3 = HI
				4 = LO
				5 = LOLO"
			::= { oPSEntry 19 }

		
		-- 1.3.6.1.4.1.3715.3.4.23.1.20
		oPSActiveInput OBJECT-TYPE
			SYNTAX INTEGER
				{
				main(1),
				reserve(2)
				}
			ACCESS read-only
			STATUS mandatory
			DESCRIPTION
				"Switch active input
				1 = main
				2 = reserve"
			::= { oPSEntry 20 }

		
		-- 1.3.6.1.4.1.3715.3.4.25
		oVATable OBJECT-TYPE
			SYNTAX SEQUENCE OF OVAEntry
			ACCESS not-accessible
			STATUS mandatory
			DESCRIPTION
				"This table contains element specific information
				for Optical Amplifier modules inserted into
				the BK backplane."
			::= { bkModules2 25 }

		
		-- 1.3.6.1.4.1.3715.3.4.25.1
		oVAEntry OBJECT-TYPE
			SYNTAX OVAEntry
			ACCESS not-accessible
			STATUS mandatory
			DESCRIPTION
				"Row in Table. Note that index is moduleIndex which is column in 
				the moduleTable defined in TELESTE-COMMON-MIB. Rows in this table
				exist only if there are corresponding rows in the moduleTable."
			INDEX { moduleId }
			::= { oVATable 1 }

		
		OVAEntry ::=
			SEQUENCE { 
				oVAInputPower
					INTEGER,
				oVAInputPowerHi
					INTEGER,
				oVAInputPowerLo
					INTEGER,
				oVAInputPowerLoLo
					INTEGER,
				oVAInputPowerDeadband
					INTEGER,
				oVAOutputParam
					INTEGER,
				oVAOutputParamHi
					INTEGER,
				oVAOutputParamLo
					INTEGER,
				oVAOutputParamLoLo
					INTEGER,
				oVAOutputParamDeadband
					INTEGER,
				oVAOutputParamOffset
					INTEGER,
				oVANumberOfPumpLasers
					INTEGER,
				oVAPumpLaser1PowerRel
					INTEGER,
				oVAPumpLaser1CurrentRel
					INTEGER,
				oVAPumpLaser1TecCurrentRel
					INTEGER,
				oVAPumpLaser1Temperature
					INTEGER,
				oVAPumpLaser2PowerRel
					INTEGER,
				oVAPumpLaser2CurrentRel
					INTEGER,
				oVAPumpLaser2TecCurrentRel
					INTEGER,
				oVAPumpLaser2Temperature
					INTEGER,
				oVAOutputControl
					INTEGER,
				oVAPumpLaserCurrentRelHi
					INTEGER,
				oVAPumpLaserCurrentRelDeadband
					INTEGER,
				oVATecCurrentRelHiHi
					INTEGER,
				oVATecCurrentRelHi
					INTEGER,
				oVATecCurrentRelDeadband
					INTEGER,
				oVASystemStatus
					INTEGER,
				oVAPumpLaserStatus
					INTEGER,
				oVAPumpLaser2Status
					INTEGER,
				oVAInputPowerStatus
					INTEGER,
				oVAOutputParamStatus
					INTEGER,
				oVAPumpLaserCurrentRelStatus
					INTEGER,
				oVAPumpLaserTecCurrentRelStatus
					INTEGER,
				oVARegulationMode
					INTEGER,
				oVAInputPowerHiHi
					INTEGER,
				oVAOutputParamHiHi
					INTEGER,
				oVAOutputParamLabel
					INTEGER,
				oVAOutputParamUnit
					INTEGER
			 }

		-- 1.3.6.1.4.1.3715.3.4.25.1.1
		oVAInputPower OBJECT-TYPE
			SYNTAX INTEGER
			ACCESS read-only
			STATUS mandatory
			DESCRIPTION
				"Optical input power. Unit 0.01 dBm."
			::= { oVAEntry 1 }

		
		-- 1.3.6.1.4.1.3715.3.4.25.1.2
		oVAInputPowerHi OBJECT-TYPE
			SYNTAX INTEGER (-1000..1000)
			ACCESS read-write
			STATUS mandatory
			DESCRIPTION
				"Optical input power HIGH warning limit. Unit 0.01 dBm."
			::= { oVAEntry 2 }

		
		-- 1.3.6.1.4.1.3715.3.4.25.1.3
		oVAInputPowerLo OBJECT-TYPE
			SYNTAX INTEGER (-1000..1000)
			ACCESS read-write
			STATUS mandatory
			DESCRIPTION
				"Optical input power LOW warning limit. Unit 0.01 dBm."
			::= { oVAEntry 3 }

		
		-- 1.3.6.1.4.1.3715.3.4.25.1.4
		oVAInputPowerLoLo OBJECT-TYPE
			SYNTAX INTEGER (-1000..1000)
			ACCESS read-write
			STATUS mandatory
			DESCRIPTION
				"Optical input power LOW alarm limit. Unit 0.01 dBm."
			::= { oVAEntry 4 }

		
		-- 1.3.6.1.4.1.3715.3.4.25.1.5
		oVAInputPowerDeadband OBJECT-TYPE
			SYNTAX INTEGER (50..500)
			ACCESS read-write
			STATUS mandatory
			DESCRIPTION
				"Optical input power deadband value. Unit 0.01 dBm."
			::= { oVAEntry 5 }

		
		-- 1.3.6.1.4.1.3715.3.4.25.1.6
		oVAOutputParam OBJECT-TYPE
			SYNTAX INTEGER
			ACCESS read-only
			STATUS mandatory
			DESCRIPTION
				"Optical output power or amplifier gain value, depends 
				on the amplifier operating mode (constant power vs. gain).
				Unit 0.01 dBm (power) or 0.01 dB (gain)."
			::= { oVAEntry 6 }

		
		-- 1.3.6.1.4.1.3715.3.4.25.1.7
		oVAOutputParamHi OBJECT-TYPE
			SYNTAX INTEGER (-1000..3000)
			ACCESS read-write
			STATUS mandatory
			DESCRIPTION
				"Optical output power or amplifier gain HIGH warning ´
				limit. Unit 0.01 dBm."
			::= { oVAEntry 7 }

		
		-- 1.3.6.1.4.1.3715.3.4.25.1.8
		oVAOutputParamLo OBJECT-TYPE
			SYNTAX INTEGER (-1000..3000)
			ACCESS read-write
			STATUS mandatory
			DESCRIPTION
				"Optical output power or amplifier gain LOW warning 
				limit. Unit 0.01 dBm."
			::= { oVAEntry 8 }

		
		-- 1.3.6.1.4.1.3715.3.4.25.1.9
		oVAOutputParamLoLo OBJECT-TYPE
			SYNTAX INTEGER (-1000..3000)
			ACCESS read-write
			STATUS mandatory
			DESCRIPTION
				"Optical output power or amplifier gain LOW alarm 
				limit. Unit 0.01 dBm."
			::= { oVAEntry 9 }

		
		-- 1.3.6.1.4.1.3715.3.4.25.1.10
		oVAOutputParamDeadband OBJECT-TYPE
			SYNTAX INTEGER (50..500)
			ACCESS read-write
			STATUS mandatory
			DESCRIPTION
				"Optical output power or amplifier gain deadband 
				value. Unit 0.01 dBm."
			::= { oVAEntry 10 }

		
		-- 1.3.6.1.4.1.3715.3.4.25.1.11
		oVAOutputParamOffset OBJECT-TYPE
			SYNTAX INTEGER (100..5000)
			ACCESS read-write
			STATUS mandatory
			DESCRIPTION
				"Optical output power or gain offset from nominal 
				value. Unit 0.01 dB."
			::= { oVAEntry 11 }

		
		-- 1.3.6.1.4.1.3715.3.4.25.1.12
		oVANumberOfPumpLasers OBJECT-TYPE
			SYNTAX INTEGER (1..2)
			ACCESS read-only
			STATUS mandatory
			DESCRIPTION
				"The number of lasers."
			::= { oVAEntry 12 }

		
		-- 1.3.6.1.4.1.3715.3.4.25.1.13
		oVAPumpLaser1PowerRel OBJECT-TYPE
			SYNTAX INTEGER
			ACCESS read-only
			STATUS mandatory
			DESCRIPTION
				"Calculated power for pump laser 1. Unit 0.01 %."
			::= { oVAEntry 13 }

		
		-- 1.3.6.1.4.1.3715.3.4.25.1.14
		oVAPumpLaser1CurrentRel OBJECT-TYPE
			SYNTAX INTEGER
			ACCESS read-only
			STATUS mandatory
			DESCRIPTION
				"Laser current relative to laser current at beginning of
				life (0... 150%), for pump laser 1. Unit 0.01 %."
			::= { oVAEntry 14 }

		
		-- 1.3.6.1.4.1.3715.3.4.25.1.15
		oVAPumpLaser1TecCurrentRel OBJECT-TYPE
			SYNTAX INTEGER
			ACCESS read-only
			STATUS mandatory
			DESCRIPTION
				"Pump 1 peltier current relative to a max.
				Value (0... 100%). Unit 0.01 %."
			::= { oVAEntry 15 }

		
		-- 1.3.6.1.4.1.3715.3.4.25.1.16
		oVAPumpLaser1Temperature OBJECT-TYPE
			SYNTAX INTEGER
			ACCESS read-only
			STATUS mandatory
			DESCRIPTION
				"Pump laser 1 temperature. Unit 0.01 degC."
			::= { oVAEntry 16 }

		
		-- 1.3.6.1.4.1.3715.3.4.25.1.17
		oVAPumpLaser2PowerRel OBJECT-TYPE
			SYNTAX INTEGER
			ACCESS read-only
			STATUS mandatory
			DESCRIPTION
				"Calculated power for pump laser 2. Unit 0.01 %."
			::= { oVAEntry 17 }

		
		-- 1.3.6.1.4.1.3715.3.4.25.1.18
		oVAPumpLaser2CurrentRel OBJECT-TYPE
			SYNTAX INTEGER
			ACCESS read-only
			STATUS mandatory
			DESCRIPTION
				"Laser current relative to laser current at beginning of
				life (0... 150%), for pump laser 2. Unit 0.01 %."
			::= { oVAEntry 18 }

		
		-- 1.3.6.1.4.1.3715.3.4.25.1.19
		oVAPumpLaser2TecCurrentRel OBJECT-TYPE
			SYNTAX INTEGER
			ACCESS read-only
			STATUS mandatory
			DESCRIPTION
				"Pump 2 peltier current relative to a max.
				Value (0... 100%). Unit 0.01 %."
			::= { oVAEntry 19 }

		
		-- 1.3.6.1.4.1.3715.3.4.25.1.20
		oVAPumpLaser2Temperature OBJECT-TYPE
			SYNTAX INTEGER
			ACCESS read-only
			STATUS mandatory
			DESCRIPTION
				"Pump laser 2 temperature. Unit 0.01 degC."
			::= { oVAEntry 20 }

		
		-- 1.3.6.1.4.1.3715.3.4.25.1.21
		oVAOutputControl OBJECT-TYPE
			SYNTAX INTEGER
				{
				outputOn(1),
				outputOff(2)
				}
			ACCESS read-write
			STATUS mandatory
			DESCRIPTION
				"Optical output control:
				outputOn(1) = optical power ON
				outputOff(2) = optical power OFF"
			::= { oVAEntry 21 }

		
		-- 1.3.6.1.4.1.3715.3.4.25.1.22
		oVAPumpLaserCurrentRelHi OBJECT-TYPE
			SYNTAX INTEGER (0..15000)
			ACCESS read-write
			STATUS mandatory
			DESCRIPTION
				"Relative Laser current HIGH warning limit (all lasers).
				Unit 0.01 %."
			::= { oVAEntry 22 }

		
		-- 1.3.6.1.4.1.3715.3.4.25.1.23
		oVAPumpLaserCurrentRelDeadband OBJECT-TYPE
			SYNTAX INTEGER (100..5000)
			ACCESS read-write
			STATUS mandatory
			DESCRIPTION
				"Relative Laser current deadband value (all lasers).
				Unit 0.01 %."
			::= { oVAEntry 23 }

		
		-- 1.3.6.1.4.1.3715.3.4.25.1.24
		oVATecCurrentRelHiHi OBJECT-TYPE
			SYNTAX INTEGER (0..10000)
			ACCESS read-write
			STATUS mandatory
			DESCRIPTION
				"Relative Peltier current HIGH alarm limit (all lasers).
				Unit 0.01 %."
			::= { oVAEntry 24 }

		
		-- 1.3.6.1.4.1.3715.3.4.25.1.25
		oVATecCurrentRelHi OBJECT-TYPE
			SYNTAX INTEGER (0..10000)
			ACCESS read-write
			STATUS mandatory
			DESCRIPTION
				"Relative Peltier current HIGH warning limit (all lasers).
				Unit 0.01 %."
			::= { oVAEntry 25 }

		
		-- 1.3.6.1.4.1.3715.3.4.25.1.26
		oVATecCurrentRelDeadband OBJECT-TYPE
			SYNTAX INTEGER (100..5000)
			ACCESS read-write
			STATUS mandatory
			DESCRIPTION
				"Relative Peltier current deadband value. Unit 0.01 %."
			::= { oVAEntry 26 }

		
		-- 1.3.6.1.4.1.3715.3.4.25.1.27
		oVASystemStatus OBJECT-TYPE
			SYNTAX INTEGER
				{
				systemOk(1),
				systemValueAtLimit(2),
				systemSwitchedOff(3)
				}
			ACCESS read-only
			STATUS mandatory
			DESCRIPTION
				"1 = System OK
				2 = Internal value at its limit
				3 = Output monitor diode defective, device switched off"
			::= { oVAEntry 27 }

		
		-- 1.3.6.1.4.1.3715.3.4.25.1.28
		oVAPumpLaserStatus OBJECT-TYPE
			SYNTAX INTEGER
				{
				laserOk(1),
				laserDefect(2)
				}
			ACCESS read-only
			STATUS mandatory
			DESCRIPTION
				"Pump laser 1 status:
				1 = Laser OK
				2 = Laser defect"
			::= { oVAEntry 28 }

		
		-- 1.3.6.1.4.1.3715.3.4.25.1.29
		oVAPumpLaser2Status OBJECT-TYPE
			SYNTAX INTEGER
				{
				laserOk(1),
				laserDefect(2)
				}
			ACCESS read-only
			STATUS mandatory
			DESCRIPTION
				"Pump laser 2 status:
				1 = Laser OK
				2 = Laser defect"
			::= { oVAEntry 29 }

		
		-- 1.3.6.1.4.1.3715.3.4.25.1.30
		oVAInputPowerStatus OBJECT-TYPE
			SYNTAX INTEGER
				{
				powerNormal(1),
				powerHIHI(2),
				powerHI(3),
				powerLO(4),
				powerLOLO(5)
				}
			ACCESS read-only
			STATUS mandatory
			DESCRIPTION
				"Input power status
				1 = OK
				2 = HIHI
				3 = HI
				4 = LO
				5 = LOLO"
			::= { oVAEntry 30 }

		
		-- 1.3.6.1.4.1.3715.3.4.25.1.31
		oVAOutputParamStatus OBJECT-TYPE
			SYNTAX INTEGER
				{
				statusNormal(1),
				statusHIHI(2),
				statusHi(3),
				statusLo(4),
				statusLOLO(5)
				}
			ACCESS read-only
			STATUS mandatory
			DESCRIPTION
				"Optical output power or amplifier gain value status, depends 
				on the amplifier operating mode (constant power vs. gain).
				Status values:
				statusNormal(1) = parameter value is within limits
				statusHIHI(2) = parameter value is above the HIHI limit
				statusHi(3) = parameter value is above the Hi limit
				statusLo(4) = parameter value is below the Lo limit
				statusLOLO(5) = parameter value is below the LOLO limit"
			::= { oVAEntry 31 }

		
		-- 1.3.6.1.4.1.3715.3.4.25.1.32
		oVAPumpLaserCurrentRelStatus OBJECT-TYPE
			SYNTAX INTEGER
				{
				biasNormal(1),
				biasHIHI(2),
				biasHI(3),
				biasLO(4),
				biasLOLO(5)
				}
			ACCESS read-only
			STATUS mandatory
			DESCRIPTION
				"Laser BIAS current status
				1 = OK
				2 = HIHI
				3 = HI
				4 = LO
				5 = LOLO"
			::= { oVAEntry 32 }

		
		-- 1.3.6.1.4.1.3715.3.4.25.1.33
		oVAPumpLaserTecCurrentRelStatus OBJECT-TYPE
			SYNTAX INTEGER
				{
				tecNormal(1),
				tecHIHI(2),
				tecHI(3),
				tecLO(4),
				tecLOLO(5)
				}
			ACCESS read-only
			STATUS mandatory
			DESCRIPTION
				"TEC status
				1 = OK
				2 = HIHI
				3 = HI
				4 = LO
				5 = LOLO"
			::= { oVAEntry 33 }

		
		-- 1.3.6.1.4.1.3715.3.4.25.1.34
		oVARegulationMode OBJECT-TYPE
			SYNTAX INTEGER
				{
				modePower(1),
				modeGain(2)
				}
			ACCESS read-write
			STATUS mandatory
			::= { oVAEntry 34 }

		
		-- 1.3.6.1.4.1.3715.3.4.25.1.35
		oVAInputPowerHiHi OBJECT-TYPE
			SYNTAX INTEGER (-1000..1000)
			ACCESS read-write
			STATUS mandatory
			DESCRIPTION
				"Optical input power HIGH alarm limit. Unit 0.01 dBm."
			::= { oVAEntry 35 }

		
		-- 1.3.6.1.4.1.3715.3.4.25.1.36
		oVAOutputParamHiHi OBJECT-TYPE
			SYNTAX INTEGER (-1000..3000)
			ACCESS read-write
			STATUS mandatory
			DESCRIPTION
				"Optical output power or amplifier gain HIGH alarm
				limit. Unit 0.01 dBm."
			::= { oVAEntry 36 }

		
		-- 1.3.6.1.4.1.3715.3.4.25.1.37
		oVAOutputParamLabel OBJECT-TYPE
			SYNTAX INTEGER
				{
				power(1),
				gain(2)
				}
			ACCESS read-only
			STATUS mandatory
			DESCRIPTION
				"Label for all OutputParam objects. Values:
				power(1) = label is 'power' (amplifier is in constant output power mode)
				gain(2) = label is 'gain' (amplifier is in constant gain mode)"
			::= { oVAEntry 37 }

		
		-- 1.3.6.1.4.1.3715.3.4.25.1.38
		oVAOutputParamUnit OBJECT-TYPE
			SYNTAX INTEGER
				{
				dBm(1),
				dB(2)
				}
			ACCESS read-only
			STATUS mandatory
			DESCRIPTION
				"Unit for all OuputParam objects. Values:
				dBm(1) = unit is dBm (amplifier is in constant output power mode)
				dB(2) = unit is dB (amplifier is in constant gain mode)"
			::= { oVAEntry 38 }

		
		-- 1.3.6.1.4.1.3715.3.4.26
		oVTxTable OBJECT-TYPE
			SYNTAX SEQUENCE OF OVTxEntry
			ACCESS not-accessible
			STATUS mandatory
			DESCRIPTION
				"This table contains element specific information
				for Fibre Transmitter (BOT86X)modules inserted into
				the BK backplane."
			::= { bkModules2 26 }

		
		-- 1.3.6.1.4.1.3715.3.4.26.1
		oVTxEntry OBJECT-TYPE
			SYNTAX OVTxEntry
			ACCESS not-accessible
			STATUS mandatory
			DESCRIPTION
				"Row in Table. Note that index is moduleIndex which is column in 
				the moduleTable defined in TELESTE-COMMON-MIB. Rows in this table
				exist only if there are corresponding rows in the moduleTable."
			INDEX { moduleId }
			::= { oVTxTable 1 }

		
		OVTxEntry ::=
			SEQUENCE { 
				oVTxOutputPower
					INTEGER,
				oVTxOutputPowerHi
					INTEGER,
				oVTxOutputPowerLo
					INTEGER,
				oVTxOutputPowerLoLo
					INTEGER,
				oVTxOutputPowerDeadband
					INTEGER,
				oVTxRfInputLevel
					INTEGER,
				oVTxRfInputLevelHi
					INTEGER,
				oVTxRfInputLevelLo
					INTEGER,
				oVTxRfInputLevelLoLo
					INTEGER,
				oVTxRfInputLevelDeadband
					INTEGER,
				oVTxRfAttenuation
					INTEGER,
				oVTxOmi
					INTEGER,
				oVTxAgcMode
					INTEGER,
				oVTxLaserCurrentRel
					INTEGER,
				oVTxLaserCurrentRelHi
					INTEGER,
				oVTxLaserCurrentRelDeadband
					INTEGER,
				oVTxTecCurrentRel
					INTEGER,
				oVTxTecCurrentRelHiHi
					INTEGER,
				oVTxTecCurrentRelHi
					INTEGER,
				oVTxTecCurrentRelDeadband
					INTEGER,
				oVTxLaserTemperature
					INTEGER,
				oVTxSbsSuppression
					INTEGER,
				oVTxChannelSpacing
					INTEGER,
				oVTxOutputControl
					INTEGER,
				oVTxRfLevelStatus
					INTEGER,
				oVTxLaserStatus
					INTEGER,
				oVTxTecStatus
					INTEGER,
				oVTxPsuStatus
					INTEGER,
				oVTxFanStatus
					INTEGER
			 }

		-- 1.3.6.1.4.1.3715.3.4.26.1.1
		oVTxOutputPower OBJECT-TYPE
			SYNTAX INTEGER
			ACCESS read-only
			STATUS mandatory
			DESCRIPTION
				"Optical output power. Unit 0.01 dBm."
			::= { oVTxEntry 1 }

		
		-- 1.3.6.1.4.1.3715.3.4.26.1.2
		oVTxOutputPowerHi OBJECT-TYPE
			SYNTAX INTEGER (-1000..3000)
			ACCESS read-write
			STATUS mandatory
			DESCRIPTION
				"Optical output power HIGH warning limit. Unit 0.01 dBm."
			::= { oVTxEntry 2 }

		
		-- 1.3.6.1.4.1.3715.3.4.26.1.3
		oVTxOutputPowerLo OBJECT-TYPE
			SYNTAX INTEGER (-1000..3000)
			ACCESS read-write
			STATUS mandatory
			DESCRIPTION
				"Optical output power LOW warning limit. Unit 0.01 dBm."
			::= { oVTxEntry 3 }

		
		-- 1.3.6.1.4.1.3715.3.4.26.1.4
		oVTxOutputPowerLoLo OBJECT-TYPE
			SYNTAX INTEGER (-1000..3000)
			ACCESS read-write
			STATUS mandatory
			DESCRIPTION
				"Optical output power LOW alarm limit. Unit 0.01 dBm."
			::= { oVTxEntry 4 }

		
		-- 1.3.6.1.4.1.3715.3.4.26.1.5
		oVTxOutputPowerDeadband OBJECT-TYPE
			SYNTAX INTEGER (50..500)
			ACCESS read-write
			STATUS mandatory
			DESCRIPTION
				"Optical output power deadband value. Unit 0.01 dBm."
			::= { oVTxEntry 5 }

		
		-- 1.3.6.1.4.1.3715.3.4.26.1.6
		oVTxRfInputLevel OBJECT-TYPE
			SYNTAX INTEGER
			ACCESS read-only
			STATUS mandatory
			DESCRIPTION
				"RF input level. Unit 0.01 dBuV."
			::= { oVTxEntry 6 }

		
		-- 1.3.6.1.4.1.3715.3.4.26.1.7
		oVTxRfInputLevelHi OBJECT-TYPE
			SYNTAX INTEGER (0..12000)
			ACCESS read-write
			STATUS mandatory
			DESCRIPTION
				"RF input HIGH warning limit. Unit 0.01 dBuV."
			::= { oVTxEntry 7 }

		
		-- 1.3.6.1.4.1.3715.3.4.26.1.8
		oVTxRfInputLevelLo OBJECT-TYPE
			SYNTAX INTEGER (0..12000)
			ACCESS read-write
			STATUS mandatory
			DESCRIPTION
				"RF input LOW warning limit. Unit 0.01 dBuV."
			::= { oVTxEntry 8 }

		
		-- 1.3.6.1.4.1.3715.3.4.26.1.9
		oVTxRfInputLevelLoLo OBJECT-TYPE
			SYNTAX INTEGER (0..12000)
			ACCESS read-write
			STATUS mandatory
			DESCRIPTION
				"RF input LOW alarm limit. Unit 0.01 dBuV."
			::= { oVTxEntry 9 }

		
		-- 1.3.6.1.4.1.3715.3.4.26.1.10
		oVTxRfInputLevelDeadband OBJECT-TYPE
			SYNTAX INTEGER (100..1000)
			ACCESS read-write
			STATUS mandatory
			DESCRIPTION
				"RF input deadband value. Unit 0.01 dBuV."
			::= { oVTxEntry 10 }

		
		-- 1.3.6.1.4.1.3715.3.4.26.1.11
		oVTxRfAttenuation OBJECT-TYPE
			SYNTAX INTEGER (-400..200)
			ACCESS read-write
			STATUS mandatory
			DESCRIPTION
				"Input RF attenuation. Unit 0.01 dB."
			::= { oVTxEntry 11 }

		
		-- 1.3.6.1.4.1.3715.3.4.26.1.12
		oVTxOmi OBJECT-TYPE
			SYNTAX INTEGER (300..360)
			ACCESS read-write
			STATUS mandatory
			DESCRIPTION
				"Optical Modulation Index. Unit 0.01 %."
			::= { oVTxEntry 12 }

		
		-- 1.3.6.1.4.1.3715.3.4.26.1.13
		oVTxAgcMode OBJECT-TYPE
			SYNTAX INTEGER
				{
				agcOff(1),
				agcCw(2),
				agcVideo(3)
				}
			ACCESS read-write
			STATUS mandatory
			DESCRIPTION
				"1 = AGC off (manual gain control)
				2 = AGC on, calibrated for unmodulated carries
				3 = AGC on, calibrated for modulated carriers"
			::= { oVTxEntry 13 }

		
		-- 1.3.6.1.4.1.3715.3.4.26.1.14
		oVTxLaserCurrentRel OBJECT-TYPE
			SYNTAX INTEGER
			ACCESS read-only
			STATUS mandatory
			DESCRIPTION
				"Laser current relative to laser current at begin of life
				(0...150%). Unit 0.01 %."
			::= { oVTxEntry 14 }

		
		-- 1.3.6.1.4.1.3715.3.4.26.1.15
		oVTxLaserCurrentRelHi OBJECT-TYPE
			SYNTAX INTEGER (0..15000)
			ACCESS read-write
			STATUS mandatory
			DESCRIPTION
				"Laser current HIGH warning limit. Unit 0.01 %."
			::= { oVTxEntry 15 }

		
		-- 1.3.6.1.4.1.3715.3.4.26.1.16
		oVTxLaserCurrentRelDeadband OBJECT-TYPE
			SYNTAX INTEGER (100..5000)
			ACCESS read-write
			STATUS mandatory
			DESCRIPTION
				"Laser current deadband value. Unit 0.01 %."
			::= { oVTxEntry 16 }

		
		-- 1.3.6.1.4.1.3715.3.4.26.1.17
		oVTxTecCurrentRel OBJECT-TYPE
			SYNTAX INTEGER
			ACCESS read-only
			STATUS mandatory
			DESCRIPTION
				"Peltier current relative to a max. value (0...100%).
				Unit 0.01 %."
			::= { oVTxEntry 17 }

		
		-- 1.3.6.1.4.1.3715.3.4.26.1.18
		oVTxTecCurrentRelHiHi OBJECT-TYPE
			SYNTAX INTEGER (0..10000)
			ACCESS read-write
			STATUS mandatory
			DESCRIPTION
				"Peltier current HIGH alarm limit. Unit 0.01 %."
			::= { oVTxEntry 18 }

		
		-- 1.3.6.1.4.1.3715.3.4.26.1.19
		oVTxTecCurrentRelHi OBJECT-TYPE
			SYNTAX INTEGER (0..10000)
			ACCESS read-write
			STATUS mandatory
			DESCRIPTION
				"Peltier current HIGH warning limit. Unit 0.01 %."
			::= { oVTxEntry 19 }

		
		-- 1.3.6.1.4.1.3715.3.4.26.1.20
		oVTxTecCurrentRelDeadband OBJECT-TYPE
			SYNTAX INTEGER (100..5000)
			ACCESS read-write
			STATUS mandatory
			DESCRIPTION
				"Peltier current deadband value. Unit 0.01 %."
			::= { oVTxEntry 20 }

		
		-- 1.3.6.1.4.1.3715.3.4.26.1.21
		oVTxLaserTemperature OBJECT-TYPE
			SYNTAX INTEGER
			ACCESS read-only
			STATUS mandatory
			DESCRIPTION
				"Laser temperature. Unit 0.01 degC."
			::= { oVTxEntry 21 }

		
		-- 1.3.6.1.4.1.3715.3.4.26.1.22
		oVTxSbsSuppression OBJECT-TYPE
			SYNTAX INTEGER (13 | 14 | 15 | 16)
			ACCESS read-write
			STATUS mandatory
			DESCRIPTION
				"The SBS suppression
				Possible values are: 13, 14, 15, 16 dBm"
			::= { oVTxEntry 22 }

		
		-- 1.3.6.1.4.1.3715.3.4.26.1.23
		oVTxChannelSpacing OBJECT-TYPE
			SYNTAX INTEGER (1..20)
			ACCESS read-write
			STATUS mandatory
			DESCRIPTION
				"The channel spacing. Unit 1 MHz."
			::= { oVTxEntry 23 }

		
		-- 1.3.6.1.4.1.3715.3.4.26.1.24
		oVTxOutputControl OBJECT-TYPE
			SYNTAX INTEGER
				{
				outputOn(1),
				outputOff(2)
				}
			ACCESS read-write
			STATUS mandatory
			DESCRIPTION
				"Optical output control:
				outputOn(1) = optical power ON
				outputOff(2) = optical power OFF"
			::= { oVTxEntry 24 }

		
		-- 1.3.6.1.4.1.3715.3.4.26.1.25
		oVTxRfLevelStatus OBJECT-TYPE
			SYNTAX INTEGER
				{
				levelNormal(1),
				levelHIHI(2),
				levelHI(3),
				levelLO(4),
				levelLOLO(5)
				}
			ACCESS read-only
			STATUS mandatory
			DESCRIPTION
				"Input RF level status
				1 = OK
				2 = HIHI
				3 = HI
				4 = LO
				5 = LOLO"
			::= { oVTxEntry 25 }

		
		-- 1.3.6.1.4.1.3715.3.4.26.1.26
		oVTxLaserStatus OBJECT-TYPE
			SYNTAX INTEGER
				{
				laserNormal(1),
				laserHIHI(2),
				laserHI(3),
				laserLO(4),
				laserLOLO(5)
				}
			ACCESS read-only
			STATUS mandatory
			DESCRIPTION
				"Pump laser status
				1 = OK
				2 = HIHI
				3 = HI
				4 = LO
				5 = LOLO"
			::= { oVTxEntry 26 }

		
		-- 1.3.6.1.4.1.3715.3.4.26.1.27
		oVTxTecStatus OBJECT-TYPE
			SYNTAX INTEGER
				{
				tecNormal(1),
				tecHIHI(2),
				tecHI(3),
				tecLO(4),
				tecLOLO(5)
				}
			ACCESS read-only
			STATUS mandatory
			DESCRIPTION
				"TEC status
				1 = OK
				2 = HIHI
				3 = HI
				4 = LO
				5 = LOLO"
			::= { oVTxEntry 27 }

		
		-- 1.3.6.1.4.1.3715.3.4.26.1.28
		oVTxPsuStatus OBJECT-TYPE
			SYNTAX INTEGER
				{
				psuNormal(1),
				psuFailure(2)
				}
			ACCESS read-only
			STATUS mandatory
			DESCRIPTION
				"Power supply status:
				1 = Both power supplies are OK
				2 = One of two power supplies fails"
			::= { oVTxEntry 28 }

		
		-- 1.3.6.1.4.1.3715.3.4.26.1.29
		oVTxFanStatus OBJECT-TYPE
			SYNTAX INTEGER
				{
				fanNormal(1),
				fanOneFail(2),
				fanTwoFail(3)
				}
			ACCESS read-only
			STATUS mandatory
			DESCRIPTION
				"Fan status:
				1 = Fans OK
				2 = One fan fails
				3 = Two fans fail
				"
			::= { oVTxEntry 29 }

		
		-- 1.3.6.1.4.1.3715.3.4.27
		oTxDTable OBJECT-TYPE
			SYNTAX SEQUENCE OF OTxDEntry
			ACCESS not-accessible
			STATUS mandatory
			DESCRIPTION
				"This table contains element specific information
				for Fibre Transmitter (BOT86X)modules inserted into
				the BK backplane."
			::= { bkModules2 27 }

		
		-- 1.3.6.1.4.1.3715.3.4.27.1
		oTxDEntry OBJECT-TYPE
			SYNTAX OTxDEntry
			ACCESS not-accessible
			STATUS mandatory
			DESCRIPTION
				"Row in Table. Note that index is moduleIndex which is column in 
				the moduleTable defined in TELESTE-COMMON-MIB. Rows in this table
				exist only if there are corresponding rows in the moduleTable."
			INDEX { moduleId }
			::= { oTxDTable 1 }

		
		OTxDEntry ::=
			SEQUENCE { 
				oTxDOutputPower
					INTEGER,
				oTxDOutputPowerRel
					INTEGER,
				oTxDOutputPowerNominal
					INTEGER,
				oTxDOutputPowerRelHiHi
					INTEGER,
				oTxDOutputPowerRelHi
					INTEGER,
				oTxDOutputPowerRelLo
					INTEGER,
				oTxDOutputPowerRelLoLo
					INTEGER,
				oTxDOutputPowerRelDeadband
					INTEGER,
				oTxDRfInputPower
					INTEGER,
				oTxDRfInputPowerHiHi
					INTEGER,
				oTxDRfInputPowerHi
					INTEGER,
				oTxDRfInputPowerLo
					INTEGER,
				oTxDRfInputPowerLoLo
					INTEGER,
				oTxDRfInputPowerDeadband
					INTEGER,
				oTxDRfGain
					INTEGER,
				oTxDRfGainMax
					INTEGER,
				oTxDRfGainHiHi
					INTEGER,
				oTxDRfGainHi
					INTEGER,
				oTxDRfGainLo
					INTEGER,
				oTxDRfGainLoLo
					INTEGER,
				oTxDRfGainDeadband
					INTEGER,
				oTxDRfGainManual
					INTEGER,
				oTxDRfSlope
					INTEGER,
				oTxDOmiRel
					INTEGER,
				oTxDOmiRelTarget
					INTEGER,
				oTxDOmiRelHiHi
					INTEGER,
				oTxDOmiRelHi
					INTEGER,
				oTxDOmiRelLo
					INTEGER,
				oTxDOmiRelLoLo
					INTEGER,
				oTxDOmiRelDeadband
					INTEGER,
				oTxDOmiNominal
					INTEGER,
				oTxDLaserWavelengthOffset
					INTEGER,
				oTxDLaserWavelengthOffsetHiHi
					INTEGER,
				oTxDLaserWavelengthOffsetHi
					INTEGER,
				oTxDLaserWavelengthOffsetLo
					INTEGER,
				oTxDLaserWavelengthOffsetLoLo
					INTEGER,
				oTxDLaserWavelengthOffsetDeadband
					INTEGER,
				oTxDLaserFreqOffset
					INTEGER,
				oTxDLaserFreqNominal
					INTEGER,
				oTxDLaserCurrentRel
					INTEGER,
				oTxDLaserCurrentRelHiHi
					INTEGER,
				oTxDLaserCurrentRelHi
					INTEGER,
				oTxDLaserCurrentRelLo
					INTEGER,
				oTxDLaserCurrentRelLoLo
					INTEGER,
				oTxDLaserCurrentRelDeadband
					INTEGER,
				oTxDLaserTempOffset
					INTEGER,
				oTxDLaserTempNominal
					INTEGER,
				oTxDLaserTempOffsetHiHi
					INTEGER,
				oTxDLaserTempOffsetHi
					INTEGER,
				oTxDLaserTempOffsetLo
					INTEGER,
				oTxDLaserTempOffsetLoLo
					INTEGER,
				oTxDLaserTempOffsetDeadband
					INTEGER,
				oTxDTecCurrentRel
					INTEGER,
				oTxDTecCurrentRelHiHi
					INTEGER,
				oTxDTecCurrentRelHi
					INTEGER,
				oTxDTecCurrentRelLo
					INTEGER,
				oTxDTecCurrentRelLoLo
					INTEGER,
				oTxDTecCurrentRelDeadband
					INTEGER,
				oTxDTecVoltage
					INTEGER,
				oTxDTecVoltageHiHi
					INTEGER,
				oTxDTecVoltageHi
					INTEGER,
				oTxDTecVoltageLo
					INTEGER,
				oTxDTecVoltageLoLo
					INTEGER,
				oTxDTecVoltageDeadband
					INTEGER,
				oTxDOutputControl
					INTEGER,
				oTxDConfig
					INTEGER,
				oTxDApcMode
					INTEGER,
				oTxDApcOperatingMode
					INTEGER,
				oTxDSbsPilotPower
					INTEGER,
				oTxDSbsPilotPowerHiHi
					INTEGER,
				oTxDSbsPilotPowerHi
					INTEGER,
				oTxDSbsPilotPowerLo
					INTEGER,
				oTxDSbsPilotPowerLoLo
					INTEGER,
				oTxDSbsPilotPowerDeadband
					INTEGER,
				oTxDFibreLength
					INTEGER,
				oTxDPilotMode
					INTEGER,
				oTxDPilotFrequency
					INTEGER,
				oTxDPilotOmiRel
					INTEGER,
				oTxDPilotLineCode
					INTEGER,
				oTxDPilotLineCodeMode
					INTEGER,
				oTxDVoltage3v3dc
					INTEGER,
				oTxDVoltage3v3dcHiHi
					INTEGER,
				oTxDVoltage3v3dcHi
					INTEGER,
				oTxDVoltage3v3dcLo
					INTEGER,
				oTxDVoltage3v3dcLoLo
					INTEGER,
				oTxDVoltage3v3dcDeadband
					INTEGER,
				oTxDVoltage5vdc
					INTEGER,
				oTxDVoltage5vdcHiHi
					INTEGER,
				oTxDVoltage5vdcHi
					INTEGER,
				oTxDVoltage5vdcLo
					INTEGER,
				oTxDVoltage5vdcLoLo
					INTEGER,
				oTxDVoltage5vdcDeadband
					INTEGER,
				oTxDVoltage10vdc
					INTEGER,
				oTxDVoltage10vdcHiHi
					INTEGER,
				oTxDVoltage10vdcHi
					INTEGER,
				oTxDVoltage10vdcLo
					INTEGER,
				oTxDVoltage10vdcLoLo
					INTEGER,
				oTxDVoltage10vdcDeadband
					INTEGER,
				oTxDVoltage24vdc
					INTEGER,
				oTxDVoltage24vdcHiHi
					INTEGER,
				oTxDVoltage24vdcHi
					INTEGER,
				oTxDVoltage24vdcLo
					INTEGER,
				oTxDVoltage24vdcLoLo
					INTEGER,
				oTxDVoltage24vdcDeadband
					INTEGER,
				oTxDVoltage2v5vdc
					INTEGER,
				oTxDVoltage2v5dcHiHi
					INTEGER,
				oTxDVoltage2v5dcHi
					INTEGER,
				oTxDVoltage2v5dcLo
					INTEGER,
				oTxDVoltage2v5dcLoLo
					INTEGER,
				oTxDVoltage2v5dcDeadband
					INTEGER,
				oTxDRfInputPowerStatus
					INTEGER,
				oTxDOutputPowerStatus
					INTEGER,
				oTxDLaserCurrentRelStatus
					INTEGER,
				oTxDTecCurrentRelStatus
					INTEGER,
				oTxDOmiRelStatus
					INTEGER,
				oTxDRfGainStatus
					INTEGER,
				oTxDLaserTempOffsetStatus
					INTEGER,
				oTxDSBSPilotPowerStatus
					INTEGER,
				oTxDLaserWavelengthOffsetStatus
					INTEGER,
				oTxDInternalVoltageStatus
					INTEGER,
				oTxDSupplyVoltageStatus
					INTEGER,
				oTxDOutputPowerRelTarget
					INTEGER,
				oTxDNcInputGain
					INTEGER,
				oTxDStandbyStatus
					INTEGER
			 }

		-- 1.3.6.1.4.1.3715.3.4.27.1.1
		oTxDOutputPower OBJECT-TYPE
			SYNTAX INTEGER
			ACCESS read-only
			STATUS mandatory
			DESCRIPTION
				"Measured optical output power value. Unit 0.01 dBm."
			::= { oTxDEntry 1 }

		
		-- 1.3.6.1.4.1.3715.3.4.27.1.2
		oTxDOutputPowerRel OBJECT-TYPE
			SYNTAX INTEGER
			ACCESS read-only
			STATUS mandatory
			DESCRIPTION
				"Measured optical output power value relative to 
				oTxDOutputPowerNominal. Unit 0.01 dB."
			::= { oTxDEntry 2 }

		
		-- 1.3.6.1.4.1.3715.3.4.27.1.3
		oTxDOutputPowerNominal OBJECT-TYPE
			SYNTAX INTEGER
			ACCESS read-only
			STATUS mandatory
			DESCRIPTION
				"Nominal optical output power value. Unit 0.01 dBm."
			::= { oTxDEntry 3 }

		
		-- 1.3.6.1.4.1.3715.3.4.27.1.4
		oTxDOutputPowerRelHiHi OBJECT-TYPE
			SYNTAX INTEGER
			ACCESS read-write
			STATUS mandatory
			DESCRIPTION
				"Relative optical output power HIGH alarm limit. Unit 0.01 dB."
			::= { oTxDEntry 4 }

		
		-- 1.3.6.1.4.1.3715.3.4.27.1.5
		oTxDOutputPowerRelHi OBJECT-TYPE
			SYNTAX INTEGER
			ACCESS read-write
			STATUS mandatory
			DESCRIPTION
				"Relative optical output power HIGH warning limit. Unit 0.01 dB."
			::= { oTxDEntry 5 }

		
		-- 1.3.6.1.4.1.3715.3.4.27.1.6
		oTxDOutputPowerRelLo OBJECT-TYPE
			SYNTAX INTEGER
			ACCESS read-write
			STATUS mandatory
			DESCRIPTION
				"Relative optical output power LOW warning limit. Unit 0.01 dB."
			::= { oTxDEntry 6 }

		
		-- 1.3.6.1.4.1.3715.3.4.27.1.7
		oTxDOutputPowerRelLoLo OBJECT-TYPE
			SYNTAX INTEGER
			ACCESS read-write
			STATUS mandatory
			DESCRIPTION
				"Relative optical output power LOW alarm limit. Unit 0.01 dB."
			::= { oTxDEntry 7 }

		
		-- 1.3.6.1.4.1.3715.3.4.27.1.8
		oTxDOutputPowerRelDeadband OBJECT-TYPE
			SYNTAX INTEGER
			ACCESS read-write
			STATUS mandatory
			DESCRIPTION
				"Relative optical output power deadband value. Unit 0.01 dB."
			::= { oTxDEntry 8 }

		
		-- 1.3.6.1.4.1.3715.3.4.27.1.9
		oTxDRfInputPower OBJECT-TYPE
			SYNTAX INTEGER
			ACCESS read-only
			STATUS mandatory
			DESCRIPTION
				"Total RF input power level. Unit 0.01 dBm."
			::= { oTxDEntry 9 }

		
		-- 1.3.6.1.4.1.3715.3.4.27.1.10
		oTxDRfInputPowerHiHi OBJECT-TYPE
			SYNTAX INTEGER
			ACCESS read-write
			STATUS mandatory
			DESCRIPTION
				"RF input power HIGH alarm limit. Unit 0.01 dBm."
			::= { oTxDEntry 10 }

		
		-- 1.3.6.1.4.1.3715.3.4.27.1.11
		oTxDRfInputPowerHi OBJECT-TYPE
			SYNTAX INTEGER
			ACCESS read-write
			STATUS mandatory
			DESCRIPTION
				"RF input power HIGH warning limit. Unit 0.01 dBm."
			::= { oTxDEntry 11 }

		
		-- 1.3.6.1.4.1.3715.3.4.27.1.12
		oTxDRfInputPowerLo OBJECT-TYPE
			SYNTAX INTEGER
			ACCESS read-write
			STATUS mandatory
			DESCRIPTION
				"RF input power LOW warning limit. Unit 0.01 dBm."
			::= { oTxDEntry 12 }

		
		-- 1.3.6.1.4.1.3715.3.4.27.1.13
		oTxDRfInputPowerLoLo OBJECT-TYPE
			SYNTAX INTEGER
			ACCESS read-write
			STATUS mandatory
			DESCRIPTION
				"RF input power LOW alarm limit. Unit 0.01 dBm."
			::= { oTxDEntry 13 }

		
		-- 1.3.6.1.4.1.3715.3.4.27.1.14
		oTxDRfInputPowerDeadband OBJECT-TYPE
			SYNTAX INTEGER
			ACCESS read-write
			STATUS mandatory
			DESCRIPTION
				"RF input power deadband value. Unit 0.01 dB."
			::= { oTxDEntry 14 }

		
		-- 1.3.6.1.4.1.3715.3.4.27.1.15
		oTxDRfGain OBJECT-TYPE
			SYNTAX INTEGER
			ACCESS read-only
			STATUS mandatory
			DESCRIPTION
				"BC input RF gain control value in APC mode. Unit 0.01 dB."
			::= { oTxDEntry 15 }

		
		-- 1.3.6.1.4.1.3715.3.4.27.1.16
		oTxDRfGainMax OBJECT-TYPE
			SYNTAX INTEGER
			ACCESS read-write
			STATUS mandatory
			DESCRIPTION
				"Maximum RF gain value (in APC mode). Unit 0.01 dB."
			::= { oTxDEntry 16 }

		
		-- 1.3.6.1.4.1.3715.3.4.27.1.17
		oTxDRfGainHiHi OBJECT-TYPE
			SYNTAX INTEGER
			ACCESS read-write
			STATUS mandatory
			DESCRIPTION
				"RF gain HIGH alarm limit. Unit 0.01 dB."
			::= { oTxDEntry 17 }

		
		-- 1.3.6.1.4.1.3715.3.4.27.1.18
		oTxDRfGainHi OBJECT-TYPE
			SYNTAX INTEGER
			ACCESS read-write
			STATUS mandatory
			DESCRIPTION
				"RF gain HIGH warning limit. Unit 0.01 dB."
			::= { oTxDEntry 18 }

		
		-- 1.3.6.1.4.1.3715.3.4.27.1.19
		oTxDRfGainLo OBJECT-TYPE
			SYNTAX INTEGER
			ACCESS read-write
			STATUS mandatory
			DESCRIPTION
				"RF gain LOW warning limit. Unit 0.01 dB."
			::= { oTxDEntry 19 }

		
		-- 1.3.6.1.4.1.3715.3.4.27.1.20
		oTxDRfGainLoLo OBJECT-TYPE
			SYNTAX INTEGER
			ACCESS read-write
			STATUS mandatory
			DESCRIPTION
				"RF gain LOW alarm limit. Unit 0.01 dB."
			::= { oTxDEntry 20 }

		
		-- 1.3.6.1.4.1.3715.3.4.27.1.21
		oTxDRfGainDeadband OBJECT-TYPE
			SYNTAX INTEGER
			ACCESS read-write
			STATUS mandatory
			DESCRIPTION
				"RF gain deadband value. Unit 0.01 dB."
			::= { oTxDEntry 21 }

		
		-- 1.3.6.1.4.1.3715.3.4.27.1.22
		oTxDRfGainManual OBJECT-TYPE
			SYNTAX INTEGER
			ACCESS read-write
			STATUS mandatory
			DESCRIPTION
				"BC input RF gain control value in APC OFF (manual) mode. Unit 0.01 dB."
			::= { oTxDEntry 22 }

		
		-- 1.3.6.1.4.1.3715.3.4.27.1.23
		oTxDRfSlope OBJECT-TYPE
			SYNTAX INTEGER
			ACCESS read-write
			STATUS mandatory
			DESCRIPTION
				"NC input RF slope control value. Unit 0.01 dB."
			::= { oTxDEntry 23 }

		
		-- 1.3.6.1.4.1.3715.3.4.27.1.24
		oTxDOmiRel OBJECT-TYPE
			SYNTAX INTEGER
			ACCESS read-only
			STATUS mandatory
			DESCRIPTION
				"Measured relative OMI. Unit 0.01 dB."
			::= { oTxDEntry 24 }

		
		-- 1.3.6.1.4.1.3715.3.4.27.1.25
		oTxDOmiRelTarget OBJECT-TYPE
			SYNTAX INTEGER
			ACCESS read-write
			STATUS mandatory
			DESCRIPTION
				"Relative OMI target for APC. Unit 0.01 dB."
			::= { oTxDEntry 25 }

		
		-- 1.3.6.1.4.1.3715.3.4.27.1.26
		oTxDOmiRelHiHi OBJECT-TYPE
			SYNTAX INTEGER
			ACCESS read-write
			STATUS mandatory
			DESCRIPTION
				"Relative OMI HIGH alarm limit. Unit 0.01 dB."
			::= { oTxDEntry 26 }

		
		-- 1.3.6.1.4.1.3715.3.4.27.1.27
		oTxDOmiRelHi OBJECT-TYPE
			SYNTAX INTEGER
			ACCESS read-write
			STATUS mandatory
			DESCRIPTION
				"Relative OMI HIGH warning limit. Unit 0.01 dB."
			::= { oTxDEntry 27 }

		
		-- 1.3.6.1.4.1.3715.3.4.27.1.28
		oTxDOmiRelLo OBJECT-TYPE
			SYNTAX INTEGER
			ACCESS read-write
			STATUS mandatory
			DESCRIPTION
				"Relative OMI LOW warning limit. Unit 0.01 dB."
			::= { oTxDEntry 28 }

		
		-- 1.3.6.1.4.1.3715.3.4.27.1.29
		oTxDOmiRelLoLo OBJECT-TYPE
			SYNTAX INTEGER
			ACCESS read-write
			STATUS mandatory
			DESCRIPTION
				"Relative OMI Low alarm limit. Unit 0.01 dB."
			::= { oTxDEntry 29 }

		
		-- 1.3.6.1.4.1.3715.3.4.27.1.30
		oTxDOmiRelDeadband OBJECT-TYPE
			SYNTAX INTEGER
			ACCESS read-write
			STATUS mandatory
			DESCRIPTION
				"Relative OMI deadband value. Unit 0.01 dB."
			::= { oTxDEntry 30 }

		
		-- 1.3.6.1.4.1.3715.3.4.27.1.31
		oTxDOmiNominal OBJECT-TYPE
			SYNTAX INTEGER
			ACCESS read-only
			STATUS mandatory
			DESCRIPTION
				"Nominal OMI. Unit 0.01 %."
			::= { oTxDEntry 31 }

		
		-- 1.3.6.1.4.1.3715.3.4.27.1.32
		oTxDLaserWavelengthOffset OBJECT-TYPE
			SYNTAX INTEGER
			ACCESS read-only
			STATUS mandatory
			DESCRIPTION
				"Laser wavelength offset from nominal value. Unit 0.01 nm."
			::= { oTxDEntry 32 }

		
		-- 1.3.6.1.4.1.3715.3.4.27.1.33
		oTxDLaserWavelengthOffsetHiHi OBJECT-TYPE
			SYNTAX INTEGER
			ACCESS read-write
			STATUS mandatory
			DESCRIPTION
				"Wavelength offset HIGH alarm limit. Unit 0.01 nm."
			::= { oTxDEntry 33 }

		
		-- 1.3.6.1.4.1.3715.3.4.27.1.34
		oTxDLaserWavelengthOffsetHi OBJECT-TYPE
			SYNTAX INTEGER
			ACCESS read-write
			STATUS mandatory
			DESCRIPTION
				"Wavelength offset HIGH warning limit. Unit 0.01 nm."
			::= { oTxDEntry 34 }

		
		-- 1.3.6.1.4.1.3715.3.4.27.1.35
		oTxDLaserWavelengthOffsetLo OBJECT-TYPE
			SYNTAX INTEGER
			ACCESS read-write
			STATUS mandatory
			DESCRIPTION
				"Wavelength offset LOW warning limit. Unit 0.01 nm."
			::= { oTxDEntry 35 }

		
		-- 1.3.6.1.4.1.3715.3.4.27.1.36
		oTxDLaserWavelengthOffsetLoLo OBJECT-TYPE
			SYNTAX INTEGER
			ACCESS read-write
			STATUS mandatory
			DESCRIPTION
				"Wavelength offset LOW alarm limit. Unit 0.01 nm."
			::= { oTxDEntry 36 }

		
		-- 1.3.6.1.4.1.3715.3.4.27.1.37
		oTxDLaserWavelengthOffsetDeadband OBJECT-TYPE
			SYNTAX INTEGER
			ACCESS read-write
			STATUS mandatory
			DESCRIPTION
				"Wavelength offset deadband value. Unit 0.01 nm."
			::= { oTxDEntry 37 }

		
		-- 1.3.6.1.4.1.3715.3.4.27.1.38
		oTxDLaserFreqOffset OBJECT-TYPE
			SYNTAX INTEGER
			ACCESS read-write
			STATUS mandatory
			DESCRIPTION
				"Laser frequency offset from nominal value. Unit 10 MHz."
			::= { oTxDEntry 38 }

		
		-- 1.3.6.1.4.1.3715.3.4.27.1.39
		oTxDLaserFreqNominal OBJECT-TYPE
			SYNTAX INTEGER
			ACCESS read-only
			STATUS mandatory
			DESCRIPTION
				"Nominal laser frequency. Unit 10 MHz."
			::= { oTxDEntry 39 }

		
		-- 1.3.6.1.4.1.3715.3.4.27.1.40
		oTxDLaserCurrentRel OBJECT-TYPE
			SYNTAX INTEGER (0..15000)
			ACCESS read-only
			STATUS mandatory
			DESCRIPTION
				"Laser BIAS current value relative to the value at the
				beginning of life (0...150%). Unit 0.01 %."
			::= { oTxDEntry 40 }

		
		-- 1.3.6.1.4.1.3715.3.4.27.1.41
		oTxDLaserCurrentRelHiHi OBJECT-TYPE
			SYNTAX INTEGER (0..15000)
			ACCESS read-write
			STATUS mandatory
			DESCRIPTION
				"Relative laser current HIGH alarm limit. Unit 0.01 %."
			::= { oTxDEntry 41 }

		
		-- 1.3.6.1.4.1.3715.3.4.27.1.42
		oTxDLaserCurrentRelHi OBJECT-TYPE
			SYNTAX INTEGER (0..15000)
			ACCESS read-write
			STATUS mandatory
			DESCRIPTION
				"Laser current HIGH warning limit. Unit 0.01 %."
			::= { oTxDEntry 42 }

		
		-- 1.3.6.1.4.1.3715.3.4.27.1.43
		oTxDLaserCurrentRelLo OBJECT-TYPE
			SYNTAX INTEGER (0..15000)
			ACCESS read-write
			STATUS mandatory
			DESCRIPTION
				"Relative laser current LOW warning limit. Unit 0.01 %."
			::= { oTxDEntry 43 }

		
		-- 1.3.6.1.4.1.3715.3.4.27.1.44
		oTxDLaserCurrentRelLoLo OBJECT-TYPE
			SYNTAX INTEGER (0..15000)
			ACCESS read-write
			STATUS mandatory
			DESCRIPTION
				"Relative laser current LOW alarm limit. Unit 0.01 %."
			::= { oTxDEntry 44 }

		
		-- 1.3.6.1.4.1.3715.3.4.27.1.45
		oTxDLaserCurrentRelDeadband OBJECT-TYPE
			SYNTAX INTEGER (0..15000)
			ACCESS read-write
			STATUS mandatory
			DESCRIPTION
				"Relative laser current deadband value. Unit 0.01 %."
			::= { oTxDEntry 45 }

		
		-- 1.3.6.1.4.1.3715.3.4.27.1.46
		oTxDLaserTempOffset OBJECT-TYPE
			SYNTAX INTEGER
			ACCESS read-only
			STATUS mandatory
			DESCRIPTION
				"Laser temperature offset from nominal laser temperature.
				Unit 0.01 degC."
			::= { oTxDEntry 46 }

		
		-- 1.3.6.1.4.1.3715.3.4.27.1.47
		oTxDLaserTempNominal OBJECT-TYPE
			SYNTAX INTEGER
			ACCESS read-only
			STATUS mandatory
			DESCRIPTION
				"Nominal laser temperature. Unit 0.01 degC."
			::= { oTxDEntry 47 }

		
		-- 1.3.6.1.4.1.3715.3.4.27.1.48
		oTxDLaserTempOffsetHiHi OBJECT-TYPE
			SYNTAX INTEGER
			ACCESS read-write
			STATUS mandatory
			DESCRIPTION
				"Laser temperature offset HIGH alarm limit. Unit 0.01 degC."
			::= { oTxDEntry 48 }

		
		-- 1.3.6.1.4.1.3715.3.4.27.1.49
		oTxDLaserTempOffsetHi OBJECT-TYPE
			SYNTAX INTEGER
			ACCESS read-write
			STATUS mandatory
			DESCRIPTION
				"Laser temperature offset HIGH warning limit. Unit 0.01 degC."
			::= { oTxDEntry 49 }

		
		-- 1.3.6.1.4.1.3715.3.4.27.1.50
		oTxDLaserTempOffsetLo OBJECT-TYPE
			SYNTAX INTEGER
			ACCESS read-write
			STATUS mandatory
			DESCRIPTION
				"Laser temperature offset LOW warning limit. Unit 0.01 degC."
			::= { oTxDEntry 50 }

		
		-- 1.3.6.1.4.1.3715.3.4.27.1.51
		oTxDLaserTempOffsetLoLo OBJECT-TYPE
			SYNTAX INTEGER
			ACCESS read-write
			STATUS mandatory
			DESCRIPTION
				"Laser temperature offset LOW alarm limit. Unit 0.01 degC."
			::= { oTxDEntry 51 }

		
		-- 1.3.6.1.4.1.3715.3.4.27.1.52
		oTxDLaserTempOffsetDeadband OBJECT-TYPE
			SYNTAX INTEGER
			ACCESS read-write
			STATUS mandatory
			DESCRIPTION
				"Laser temperature offset deadband value. Unit 0.01 degC."
			::= { oTxDEntry 52 }

		
		-- 1.3.6.1.4.1.3715.3.4.27.1.53
		oTxDTecCurrentRel OBJECT-TYPE
			SYNTAX INTEGER (-10000..10000)
			ACCESS read-only
			STATUS mandatory
			DESCRIPTION
				"TEC current relative to a max. value (0...100%).
				Unit 0.01 %.
				Cooling = positive value, heating = negative value."
			::= { oTxDEntry 53 }

		
		-- 1.3.6.1.4.1.3715.3.4.27.1.54
		oTxDTecCurrentRelHiHi OBJECT-TYPE
			SYNTAX INTEGER (-10000..10000)
			ACCESS read-write
			STATUS mandatory
			DESCRIPTION
				"Relative TEC current HIGH alarm limit. Unit 0.01 %."
			::= { oTxDEntry 54 }

		
		-- 1.3.6.1.4.1.3715.3.4.27.1.55
		oTxDTecCurrentRelHi OBJECT-TYPE
			SYNTAX INTEGER (-10000..10000)
			ACCESS read-write
			STATUS mandatory
			DESCRIPTION
				"Relative TEC current HIGH warning limit. Unit 0.01 %."
			::= { oTxDEntry 55 }

		
		-- 1.3.6.1.4.1.3715.3.4.27.1.56
		oTxDTecCurrentRelLo OBJECT-TYPE
			SYNTAX INTEGER (-10000..10000)
			ACCESS read-write
			STATUS mandatory
			DESCRIPTION
				"Relative TEC current LOW warning limit. Unit 0.01 %."
			::= { oTxDEntry 56 }

		
		-- 1.3.6.1.4.1.3715.3.4.27.1.57
		oTxDTecCurrentRelLoLo OBJECT-TYPE
			SYNTAX INTEGER (-10000..10000)
			ACCESS read-write
			STATUS mandatory
			DESCRIPTION
				"Relative TEC current LOW alarm limit. Unit 0.01 %."
			::= { oTxDEntry 57 }

		
		-- 1.3.6.1.4.1.3715.3.4.27.1.58
		oTxDTecCurrentRelDeadband OBJECT-TYPE
			SYNTAX INTEGER (-10000..10000)
			ACCESS read-write
			STATUS mandatory
			DESCRIPTION
				"Relative TEC current deadband value. Unit 0.01 %."
			::= { oTxDEntry 58 }

		
		-- 1.3.6.1.4.1.3715.3.4.27.1.59
		oTxDTecVoltage OBJECT-TYPE
			SYNTAX INTEGER
			ACCESS read-only
			STATUS mandatory
			DESCRIPTION
				"TEC voltage. Unit 0.01 V."
			::= { oTxDEntry 59 }

		
		-- 1.3.6.1.4.1.3715.3.4.27.1.60
		oTxDTecVoltageHiHi OBJECT-TYPE
			SYNTAX INTEGER
			ACCESS read-write
			STATUS mandatory
			DESCRIPTION
				"TEC voltage HIGH alarm limit. Unit 0.01 V."
			::= { oTxDEntry 60 }

		
		-- 1.3.6.1.4.1.3715.3.4.27.1.61
		oTxDTecVoltageHi OBJECT-TYPE
			SYNTAX INTEGER
			ACCESS read-write
			STATUS mandatory
			DESCRIPTION
				"TEC voltage HIGH warning limit. Unit 0.01 V."
			::= { oTxDEntry 61 }

		
		-- 1.3.6.1.4.1.3715.3.4.27.1.62
		oTxDTecVoltageLo OBJECT-TYPE
			SYNTAX INTEGER
			ACCESS read-write
			STATUS mandatory
			DESCRIPTION
				"TEC voltage LOW warning limit. Unit 0.01 V."
			::= { oTxDEntry 62 }

		
		-- 1.3.6.1.4.1.3715.3.4.27.1.63
		oTxDTecVoltageLoLo OBJECT-TYPE
			SYNTAX INTEGER
			ACCESS read-write
			STATUS mandatory
			DESCRIPTION
				"TEC voltage LOW alarm limit. Unit 0.01 V."
			::= { oTxDEntry 63 }

		
		-- 1.3.6.1.4.1.3715.3.4.27.1.64
		oTxDTecVoltageDeadband OBJECT-TYPE
			SYNTAX INTEGER
			ACCESS read-write
			STATUS mandatory
			DESCRIPTION
				"TEC voltage deadband value. Unit 0.01 V."
			::= { oTxDEntry 64 }

		
		-- 1.3.6.1.4.1.3715.3.4.27.1.65
		oTxDOutputControl OBJECT-TYPE
			SYNTAX INTEGER
				{
				outputOff(1),
				outputOn(2)
				}
			ACCESS read-write
			STATUS mandatory
			DESCRIPTION
				"Optical output control:
				outputOff(1) = optical power OFF
				outputOn(2) = optical power ON
				"
			::= { oTxDEntry 65 }

		
		-- 1.3.6.1.4.1.3715.3.4.27.1.66
		oTxDConfig OBJECT-TYPE
			SYNTAX INTEGER
			ACCESS read-only
			STATUS mandatory
			DESCRIPTION
				"Transmitter configuration information.
				Bit based encoding:
				bit 0: 1 = Cooled laser
				bit 1: 1 = LON module used
				bit 2: 1 = Wavelength monitor supported
				bit 3: 1 = ITU frequency not adjustable
				bit 4: 1 = ITU frequency not valid"
			::= { oTxDEntry 66 }

		
		-- 1.3.6.1.4.1.3715.3.4.27.1.67
		oTxDApcMode OBJECT-TYPE
			SYNTAX INTEGER
				{
				apcOFF(1),
				apcON(2)
				}
			ACCESS read-write
			STATUS mandatory
			DESCRIPTION
				"APC (automatic power control) mode:
				1 = APC OFF
				2 = APC ON
				Automatic power control keeps the laser drive RF
				power constant."
			::= { oTxDEntry 67 }

		
		-- 1.3.6.1.4.1.3715.3.4.27.1.68
		oTxDApcOperatingMode OBJECT-TYPE
			SYNTAX INTEGER
				{
				apcNormal(1),
				apcLowNoise(2),
				apcLowDistortion(3)
				}
			ACCESS read-write
			STATUS mandatory
			DESCRIPTION
				"APC operating mode:
				1 = normal
				2 = low noise
				3 = low distortion"
			::= { oTxDEntry 68 }

		
		-- 1.3.6.1.4.1.3715.3.4.27.1.69
		oTxDSbsPilotPower OBJECT-TYPE
			SYNTAX INTEGER
			ACCESS read-only
			STATUS mandatory
			DESCRIPTION
				"SBS suppression pilot tone power. Unit 0.01 dBm."
			::= { oTxDEntry 69 }

		
		-- 1.3.6.1.4.1.3715.3.4.27.1.70
		oTxDSbsPilotPowerHiHi OBJECT-TYPE
			SYNTAX INTEGER
			ACCESS read-write
			STATUS mandatory
			DESCRIPTION
				"SBS pilot power HIGH alarm limit. Unit 0.01 dBm."
			::= { oTxDEntry 70 }

		
		-- 1.3.6.1.4.1.3715.3.4.27.1.71
		oTxDSbsPilotPowerHi OBJECT-TYPE
			SYNTAX INTEGER
			ACCESS read-write
			STATUS mandatory
			DESCRIPTION
				"SBS pilot power HIGH warning limit. Unit 0.01 dBm."
			::= { oTxDEntry 71 }

		
		-- 1.3.6.1.4.1.3715.3.4.27.1.72
		oTxDSbsPilotPowerLo OBJECT-TYPE
			SYNTAX INTEGER
			ACCESS read-write
			STATUS mandatory
			DESCRIPTION
				"SBS pilot power LOW warning limit. Unit 0.01 dBm."
			::= { oTxDEntry 72 }

		
		-- 1.3.6.1.4.1.3715.3.4.27.1.73
		oTxDSbsPilotPowerLoLo OBJECT-TYPE
			SYNTAX INTEGER
			ACCESS read-write
			STATUS mandatory
			DESCRIPTION
				"SBS pilot power LOW alarm limit. Unit 0.01 dBm."
			::= { oTxDEntry 73 }

		
		-- 1.3.6.1.4.1.3715.3.4.27.1.74
		oTxDSbsPilotPowerDeadband OBJECT-TYPE
			SYNTAX INTEGER
			ACCESS read-write
			STATUS mandatory
			DESCRIPTION
				"SBS pilot power deadband value. Unit 0.01 dB."
			::= { oTxDEntry 74 }

		
		-- 1.3.6.1.4.1.3715.3.4.27.1.75
		oTxDFibreLength OBJECT-TYPE
			SYNTAX INTEGER
			ACCESS read-write
			STATUS mandatory
			DESCRIPTION
				"Estimated fibre length. Unit 0.01 km."
			::= { oTxDEntry 75 }

		
		-- 1.3.6.1.4.1.3715.3.4.27.1.76
		oTxDPilotMode OBJECT-TYPE
			SYNTAX INTEGER
				{
				pilotOFF(1),
				pilotON(2)
				}
			ACCESS read-write
			STATUS mandatory
			DESCRIPTION
				"Pilot operation mode:
				1 = pilot OFF
				2 = pilot ON"
			::= { oTxDEntry 76 }

		
		-- 1.3.6.1.4.1.3715.3.4.27.1.77
		oTxDPilotFrequency OBJECT-TYPE
			SYNTAX INTEGER
				{
				freq307kHz(1),
				freq614kHz(2),
				freq1229kHz(3),
				freq2458kHz(4)
				}
			ACCESS read-write
			STATUS mandatory
			DESCRIPTION
				"Pilot tone frequency:
				1 = 307 kHz
				2 = 614 kHz
				3 = 1229 kHz
				4 = 2458 kHz"
			::= { oTxDEntry 77 }

		
		-- 1.3.6.1.4.1.3715.3.4.27.1.78
		oTxDPilotOmiRel OBJECT-TYPE
			SYNTAX INTEGER
			ACCESS read-write
			STATUS mandatory
			DESCRIPTION
				"Relative pilot OMI value. Unit 0.01 dB."
			::= { oTxDEntry 78 }

		
		-- 1.3.6.1.4.1.3715.3.4.27.1.79
		oTxDPilotLineCode OBJECT-TYPE
			SYNTAX INTEGER (0..511)
			ACCESS read-write
			STATUS mandatory
			DESCRIPTION
				"Line code number, 0...511."
			::= { oTxDEntry 79 }

		
		-- 1.3.6.1.4.1.3715.3.4.27.1.80
		oTxDPilotLineCodeMode OBJECT-TYPE
			SYNTAX INTEGER
				{
				lineCodeOff(1),
				lineCodeOn(2)
				}
			ACCESS read-write
			STATUS mandatory
			DESCRIPTION
				"Line code mode:
				1 = line code OFF
				2 = line code ON"
			::= { oTxDEntry 80 }

		
		-- 1.3.6.1.4.1.3715.3.4.27.1.81
		oTxDVoltage3v3dc OBJECT-TYPE
			SYNTAX INTEGER
			ACCESS read-only
			STATUS mandatory
			DESCRIPTION
				"Internal + 3.3 VDC voltage. Unit 0.01 V."
			::= { oTxDEntry 81 }

		
		-- 1.3.6.1.4.1.3715.3.4.27.1.82
		oTxDVoltage3v3dcHiHi OBJECT-TYPE
			SYNTAX INTEGER
			ACCESS read-write
			STATUS mandatory
			DESCRIPTION
				"Internal + 3.3 VDC voltage HIGH alarm limit. Unit 0.01 V."
			::= { oTxDEntry 82 }

		
		-- 1.3.6.1.4.1.3715.3.4.27.1.83
		oTxDVoltage3v3dcHi OBJECT-TYPE
			SYNTAX INTEGER
			ACCESS read-write
			STATUS mandatory
			DESCRIPTION
				"Internal + 3.3 VDC voltage HIGH warning limit. Unit 0.01 V."
			::= { oTxDEntry 83 }

		
		-- 1.3.6.1.4.1.3715.3.4.27.1.84
		oTxDVoltage3v3dcLo OBJECT-TYPE
			SYNTAX INTEGER
			ACCESS read-write
			STATUS mandatory
			DESCRIPTION
				"Internal + 3.3 VDC voltage LOW warning limit. Unit 0.01 V."
			::= { oTxDEntry 84 }

		
		-- 1.3.6.1.4.1.3715.3.4.27.1.85
		oTxDVoltage3v3dcLoLo OBJECT-TYPE
			SYNTAX INTEGER
			ACCESS read-write
			STATUS mandatory
			DESCRIPTION
				"Internal + 3.3 VDC voltage LOW alarm limit. Unit 0.01 V."
			::= { oTxDEntry 85 }

		
		-- 1.3.6.1.4.1.3715.3.4.27.1.86
		oTxDVoltage3v3dcDeadband OBJECT-TYPE
			SYNTAX INTEGER
			ACCESS read-write
			STATUS mandatory
			DESCRIPTION
				"Internal + 3.3 VDC voltage deadband value. Unit 0.01 V."
			::= { oTxDEntry 86 }

		
		-- 1.3.6.1.4.1.3715.3.4.27.1.87
		oTxDVoltage5vdc OBJECT-TYPE
			SYNTAX INTEGER
			ACCESS read-only
			STATUS mandatory
			DESCRIPTION
				"Internal + 5 VDC voltage. Unit 0.01 V."
			::= { oTxDEntry 87 }

		
		-- 1.3.6.1.4.1.3715.3.4.27.1.88
		oTxDVoltage5vdcHiHi OBJECT-TYPE
			SYNTAX INTEGER
			ACCESS read-write
			STATUS mandatory
			DESCRIPTION
				"Internal + 5 VDC voltage HIGH alarm limit. Unit 0.01 V."
			::= { oTxDEntry 88 }

		
		-- 1.3.6.1.4.1.3715.3.4.27.1.89
		oTxDVoltage5vdcHi OBJECT-TYPE
			SYNTAX INTEGER
			ACCESS read-write
			STATUS mandatory
			DESCRIPTION
				"Internal + 5 VDC voltage HIGH warning limit. Unit 0.01 V."
			::= { oTxDEntry 89 }

		
		-- 1.3.6.1.4.1.3715.3.4.27.1.90
		oTxDVoltage5vdcLo OBJECT-TYPE
			SYNTAX INTEGER
			ACCESS read-write
			STATUS mandatory
			DESCRIPTION
				"Internal + 5 VDC voltage LOW warning limit. Unit 0.01 V."
			::= { oTxDEntry 90 }

		
		-- 1.3.6.1.4.1.3715.3.4.27.1.91
		oTxDVoltage5vdcLoLo OBJECT-TYPE
			SYNTAX INTEGER
			ACCESS read-write
			STATUS mandatory
			DESCRIPTION
				"Internal + 5 VDC voltage LOW alarm limit. Unit 0.01 V."
			::= { oTxDEntry 91 }

		
		-- 1.3.6.1.4.1.3715.3.4.27.1.92
		oTxDVoltage5vdcDeadband OBJECT-TYPE
			SYNTAX INTEGER
			ACCESS read-write
			STATUS mandatory
			DESCRIPTION
				"Internal + 5 VDC voltage deadband value. Unit 0.01 V."
			::= { oTxDEntry 92 }

		
		-- 1.3.6.1.4.1.3715.3.4.27.1.93
		oTxDVoltage10vdc OBJECT-TYPE
			SYNTAX INTEGER
			ACCESS read-only
			STATUS mandatory
			DESCRIPTION
				"Internal + 10 VDC voltage. Unit 0.01 V."
			::= { oTxDEntry 93 }

		
		-- 1.3.6.1.4.1.3715.3.4.27.1.94
		oTxDVoltage10vdcHiHi OBJECT-TYPE
			SYNTAX INTEGER
			ACCESS read-write
			STATUS mandatory
			DESCRIPTION
				"Internal + 10 VDC voltage HIGH alarm limit. Unit 0.01 V."
			::= { oTxDEntry 94 }

		
		-- 1.3.6.1.4.1.3715.3.4.27.1.95
		oTxDVoltage10vdcHi OBJECT-TYPE
			SYNTAX INTEGER
			ACCESS read-write
			STATUS mandatory
			DESCRIPTION
				"Internal + 10 VDC voltage HIGH warning limit. Unit 0.01 V."
			::= { oTxDEntry 95 }

		
		-- 1.3.6.1.4.1.3715.3.4.27.1.96
		oTxDVoltage10vdcLo OBJECT-TYPE
			SYNTAX INTEGER
			ACCESS read-write
			STATUS mandatory
			DESCRIPTION
				"Internal + 10 VDC voltage LOW warning limit. Unit 0.01 V."
			::= { oTxDEntry 96 }

		
		-- 1.3.6.1.4.1.3715.3.4.27.1.97
		oTxDVoltage10vdcLoLo OBJECT-TYPE
			SYNTAX INTEGER
			ACCESS read-write
			STATUS mandatory
			DESCRIPTION
				"Internal + 10 VDC voltage LOW alarm limit. Unit 0.01 V."
			::= { oTxDEntry 97 }

		
		-- 1.3.6.1.4.1.3715.3.4.27.1.98
		oTxDVoltage10vdcDeadband OBJECT-TYPE
			SYNTAX INTEGER
			ACCESS read-write
			STATUS mandatory
			DESCRIPTION
				"Internal + 10 VDC voltage deadband value. Unit 0.01 V."
			::= { oTxDEntry 98 }

		
		-- 1.3.6.1.4.1.3715.3.4.27.1.99
		oTxDVoltage24vdc OBJECT-TYPE
			SYNTAX INTEGER
			ACCESS read-only
			STATUS mandatory
			DESCRIPTION
				"External + 24 VDC voltage. Unit 0.01 V."
			::= { oTxDEntry 99 }

		
		-- 1.3.6.1.4.1.3715.3.4.27.1.100
		oTxDVoltage24vdcHiHi OBJECT-TYPE
			SYNTAX INTEGER
			ACCESS read-write
			STATUS mandatory
			DESCRIPTION
				"External + 24 VDC voltage HIGH alarm limit. Unit 0.01 V."
			::= { oTxDEntry 100 }

		
		-- 1.3.6.1.4.1.3715.3.4.27.1.101
		oTxDVoltage24vdcHi OBJECT-TYPE
			SYNTAX INTEGER
			ACCESS read-write
			STATUS mandatory
			DESCRIPTION
				"External + 24 VDC voltage HIGH warning limit. Unit 0.01 V."
			::= { oTxDEntry 101 }

		
		-- 1.3.6.1.4.1.3715.3.4.27.1.102
		oTxDVoltage24vdcLo OBJECT-TYPE
			SYNTAX INTEGER
			ACCESS read-write
			STATUS mandatory
			DESCRIPTION
				"External + 24 VDC voltage LOW warning limit. Unit 0.01 V."
			::= { oTxDEntry 102 }

		
		-- 1.3.6.1.4.1.3715.3.4.27.1.103
		oTxDVoltage24vdcLoLo OBJECT-TYPE
			SYNTAX INTEGER
			ACCESS read-write
			STATUS mandatory
			DESCRIPTION
				"External + 24 VDC voltage LOW alarm limit. Unit 0.01 V."
			::= { oTxDEntry 103 }

		
		-- 1.3.6.1.4.1.3715.3.4.27.1.104
		oTxDVoltage24vdcDeadband OBJECT-TYPE
			SYNTAX INTEGER
			ACCESS read-write
			STATUS mandatory
			DESCRIPTION
				"External + 24 VDC voltage deadband value. Unit 0.01 V."
			::= { oTxDEntry 104 }

		
		-- 1.3.6.1.4.1.3715.3.4.27.1.105
		oTxDVoltage2v5vdc OBJECT-TYPE
			SYNTAX INTEGER
			ACCESS read-only
			STATUS mandatory
			DESCRIPTION
				"Internal - 2.5 VDC voltage. Unit 0.01 V."
			::= { oTxDEntry 105 }

		
		-- 1.3.6.1.4.1.3715.3.4.27.1.106
		oTxDVoltage2v5dcHiHi OBJECT-TYPE
			SYNTAX INTEGER
			ACCESS read-write
			STATUS mandatory
			DESCRIPTION
				"Internal - 2.5 VDC voltage HIGH alarm limit. Unit 0.01 V."
			::= { oTxDEntry 106 }

		
		-- 1.3.6.1.4.1.3715.3.4.27.1.107
		oTxDVoltage2v5dcHi OBJECT-TYPE
			SYNTAX INTEGER
			ACCESS read-write
			STATUS mandatory
			DESCRIPTION
				"Internal - 2.5 VDC voltage HIGH warning limit. Unit 0.01 V."
			::= { oTxDEntry 107 }

		
		-- 1.3.6.1.4.1.3715.3.4.27.1.108
		oTxDVoltage2v5dcLo OBJECT-TYPE
			SYNTAX INTEGER
			ACCESS read-write
			STATUS mandatory
			DESCRIPTION
				"Internal - 2.5 VDC voltage LOW warning limit. Unit 0.01 V."
			::= { oTxDEntry 108 }

		
		-- 1.3.6.1.4.1.3715.3.4.27.1.109
		oTxDVoltage2v5dcLoLo OBJECT-TYPE
			SYNTAX INTEGER
			ACCESS read-write
			STATUS mandatory
			DESCRIPTION
				"Internal - 2.5 VDC voltage LOW alarm limit. Unit 0.01 V."
			::= { oTxDEntry 109 }

		
		-- 1.3.6.1.4.1.3715.3.4.27.1.110
		oTxDVoltage2v5dcDeadband OBJECT-TYPE
			SYNTAX INTEGER
			ACCESS read-write
			STATUS mandatory
			DESCRIPTION
				"Internal - 2.5 VDC voltage deadband value. Unit 0.01 V."
			::= { oTxDEntry 110 }

		
		-- 1.3.6.1.4.1.3715.3.4.27.1.111
		oTxDRfInputPowerStatus OBJECT-TYPE
			SYNTAX INTEGER
				{
				levelNormal(1),
				levelHIHI(2),
				levelHI(3),
				levelLO(4),
				levelLOLO(5)
				}
			ACCESS read-only
			STATUS mandatory
			DESCRIPTION
				"Input RF Power status:
				1 = OK
				2 = HIHI
				3 = HI
				4 = LO
				5 = LOLO"
			::= { oTxDEntry 111 }

		
		-- 1.3.6.1.4.1.3715.3.4.27.1.112
		oTxDOutputPowerStatus OBJECT-TYPE
			SYNTAX INTEGER
				{
				powerNormal(1),
				powerHIHI(2),
				powerHI(3),
				powerLO(4),
				powerLOLO(5)
				}
			ACCESS read-only
			STATUS mandatory
			DESCRIPTION
				"Optical output power status:
				1 = OK
				2 = HIHI
				3 = HI
				4 = LO
				5 = LOLO"
			::= { oTxDEntry 112 }

		
		-- 1.3.6.1.4.1.3715.3.4.27.1.113
		oTxDLaserCurrentRelStatus OBJECT-TYPE
			SYNTAX INTEGER
				{
				currentNormal(1),
				currentHIHI(2),
				currentHI(3),
				currentLO(4),
				currentLOLO(5)
				}
			ACCESS read-only
			STATUS mandatory
			DESCRIPTION
				"Laser bias current status:
				1 = OK
				2 = HIHI
				3 = HI
				4 = LO
				5 = LOLO"
			::= { oTxDEntry 113 }

		
		-- 1.3.6.1.4.1.3715.3.4.27.1.114
		oTxDTecCurrentRelStatus OBJECT-TYPE
			SYNTAX INTEGER
				{
				currentNormal(1),
				currentHIHI(2),
				currentHI(3),
				currentLO(4),
				currentLOLO(5)
				}
			ACCESS read-only
			STATUS mandatory
			DESCRIPTION
				"TEC current status:
				1 = OK
				2 = HIHI
				3 = HI
				4 = LO
				5 = LOLO"
			::= { oTxDEntry 114 }

		
		-- 1.3.6.1.4.1.3715.3.4.27.1.115
		oTxDOmiRelStatus OBJECT-TYPE
			SYNTAX INTEGER
				{
				omiNormal(1),
				omiHIHI(2),
				omiHI(3),
				omiLO(4),
				omiLOLO(5)
				}
			ACCESS read-only
			STATUS mandatory
			DESCRIPTION
				"Relative OMI status:
				1 = OK
				2 = HIHI
				3 = HI
				4 = LO
				5 = LOLO"
			::= { oTxDEntry 115 }

		
		-- 1.3.6.1.4.1.3715.3.4.27.1.116
		oTxDRfGainStatus OBJECT-TYPE
			SYNTAX INTEGER
				{
				gainNormal(1),
				gainHIHI(2),
				gainHI(3),
				gainLO(4),
				gainLOLO(5)
				}
			ACCESS read-only
			STATUS mandatory
			DESCRIPTION
				"Input RF gain status:
				1 = OK
				2 = HIHI
				3 = HI
				4 = LO
				5 = LOLO"
			::= { oTxDEntry 116 }

		
		-- 1.3.6.1.4.1.3715.3.4.27.1.117
		oTxDLaserTempOffsetStatus OBJECT-TYPE
			SYNTAX INTEGER
				{
				tempNormal(1),
				tempHIHI(2),
				tempHI(3),
				tempLO(4),
				tempLOLO(5)
				}
			ACCESS read-only
			STATUS mandatory
			DESCRIPTION
				"Laser temperature offset status:
				1 = OK
				2 = HIHI
				3 = HI
				4 = LO
				5 = LOLO"
			::= { oTxDEntry 117 }

		
		-- 1.3.6.1.4.1.3715.3.4.27.1.118
		oTxDSBSPilotPowerStatus OBJECT-TYPE
			SYNTAX INTEGER
				{
				pilotNormal(1),
				pilotHIHI(2),
				pilotHI(3),
				pilotLO(4),
				pilotLOLO(5)
				}
			ACCESS read-only
			STATUS mandatory
			DESCRIPTION
				"SBS pilot power status:
				1 = OK
				2 = HIHI
				3 = HI
				4 = LO
				5 = LOLO"
			::= { oTxDEntry 118 }

		
		-- 1.3.6.1.4.1.3715.3.4.27.1.119
		oTxDLaserWavelengthOffsetStatus OBJECT-TYPE
			SYNTAX INTEGER
				{
				offsetNormal(1),
				offsetHIHI(2),
				offsetHI(3),
				offsetLO(4),
				offsetLOLO(5)
				}
			ACCESS read-only
			STATUS mandatory
			DESCRIPTION
				"Wavelength offset status:
				1 = OK
				2 = HIHI
				3 = HI
				4 = LO
				5 = LOLO"
			::= { oTxDEntry 119 }

		
		-- 1.3.6.1.4.1.3715.3.4.27.1.120
		oTxDInternalVoltageStatus OBJECT-TYPE
			SYNTAX INTEGER
				{
				voltageNormal(1),
				voltageAlarm(2),
				voltageHI(3),
				voltageLO(4),
				voltageLOLO(5)
				}
			ACCESS read-only
			STATUS mandatory
			DESCRIPTION
				"Internal supply voltage status:
				1 = OK
				2 = HIHI
				3 = HI
				4 = LO
				5 = LOLO
				This is a common status object for all internal voltages."
			::= { oTxDEntry 120 }

		
		-- 1.3.6.1.4.1.3715.3.4.27.1.121
		oTxDSupplyVoltageStatus OBJECT-TYPE
			SYNTAX INTEGER
				{
				voltageNormal(1),
				voltageHIHI(2),
				voltageHI(3),
				voltageLO(4),
				voltageLOLO(5)
				}
			ACCESS read-only
			STATUS mandatory
			DESCRIPTION
				"+24 V supply voltage status:
				1 = OK
				2 = HIHI
				3 = HI
				4 = LO
				5 = LOLO"
			::= { oTxDEntry 121 }

		
		-- 1.3.6.1.4.1.3715.3.4.27.1.122
		oTxDOutputPowerRelTarget OBJECT-TYPE
			SYNTAX INTEGER
			ACCESS read-write
			STATUS mandatory
			DESCRIPTION
				"Optical output power target relative to oTxDOutputPowerNominal.
				Unit 0.01 dB."
			::= { oTxDEntry 122 }

		
		-- 1.3.6.1.4.1.3715.3.4.27.1.123
		oTxDNcInputGain OBJECT-TYPE
			SYNTAX INTEGER
			ACCESS read-write
			STATUS mandatory
			DESCRIPTION
				"NC input RF gain control value. Unit 0.01 dB."
			::= { oTxDEntry 123 }

		
		-- 1.3.6.1.4.1.3715.3.4.27.1.124
		oTxDStandbyStatus OBJECT-TYPE
			SYNTAX INTEGER
				{
				noStandby(1),
				standby(2)
				}
			ACCESS read-only
			STATUS mandatory
			DESCRIPTION
				"Standby status, values:
				noStandby(1)= active (optical output is on)
				standby(2) = standby (optical output off)"
			::= { oTxDEntry 124 }

		
		-- 1.3.6.1.4.1.3715.3.4.28
		oRRxTable OBJECT-TYPE
			SYNTAX SEQUENCE OF ORRxEntry
			ACCESS not-accessible
			STATUS mandatory
			DESCRIPTION
				"oRxTable contains element specific information
				for Optical Receiver (BOR26X) modules inserted
				into the BK backplane. 
				"
			::= { bkModules2 28 }

		
		-- 1.3.6.1.4.1.3715.3.4.28.1
		oRRxEntry OBJECT-TYPE
			SYNTAX ORRxEntry
			ACCESS not-accessible
			STATUS mandatory
			DESCRIPTION
				"Row in Table. Note that index is moduleIndex which is column in 
				the moduleTable defined in TELESTE-COMMON-MIB. Rows in this table
				exist only if there are corresponding rows in the moduleTable."
			INDEX { moduleId }
			::= { oRRxTable 1 }

		
		ORRxEntry ::=
			SEQUENCE { 
				oRRx1InputPower
					INTEGER,
				oRRx1InputPowerHiHi
					INTEGER,
				oRRx1InputPowerHi
					INTEGER,
				oRRx1InputPowerLo
					INTEGER,
				oRRx1InputPowerLoLo
					INTEGER,
				oRRx1InputPowerDeadband
					INTEGER,
				oRRx1CodeMainReserve
					INTEGER,
				oRRx1CodeNumberRcvd
					INTEGER,
				oRRx1CodeNumberExptd
					INTEGER,
				oRRx1Mode
					INTEGER,
				oRRx1IngressSwitch
					INTEGER,
				oRRx1OutputLevel
					INTEGER,
				oRRx2InputPower
					INTEGER,
				oRRx2InputPowerHiHi
					INTEGER,
				oRRx2InputPowerHi
					INTEGER,
				oRRx2InputPowerLo
					INTEGER,
				oRRx2InputPowerLoLo
					INTEGER,
				oRRx2InputPowerDeadband
					INTEGER,
				oRRx2CodeMainReserve
					INTEGER,
				oRRx2CodeNumberRcvd
					INTEGER,
				oRRx2CodeNumberExptd
					INTEGER,
				oRRx2Mode
					INTEGER,
				oRRx2IngresSwitch
					INTEGER,
				oRRx2OutputLevel
					INTEGER,
				oRRxCmnMainReserve
					INTEGER,
				oRRxCmnCodeUsage
					INTEGER,
				oRRxCmnOutputMode
					INTEGER,
				oRRxCmnRedundancyMode
					INTEGER,
				oRRx1Status
					INTEGER,
				oRRx1InputPowerStatus
					INTEGER,
				oRRx1PilotStatus
					INTEGER,
				oRRx1CodeStatus
					INTEGER,
				oRRx2Status
					INTEGER,
				oRRx2InputPowerStatus
					INTEGER,
				oRRx2PilotStatus
					INTEGER,
				oRRx2CodeStatus
					INTEGER,
				oRRxCmnLinkStatus
					INTEGER,
				oRRxCmnIngressSwitchStatus
					INTEGER,
				oRRxCmnNominalPortControl
					INTEGER,
				oRRxCmnNotchControl
					INTEGER,
				oRRx1Gain
					INTEGER,
				oRRx1AlcMode
					INTEGER,
				oRRx1AlcStatus
					INTEGER,
				oRRx2Gain
					INTEGER,
				oRRxCmnSlope
					INTEGER
			 }

		-- 1.3.6.1.4.1.3715.3.4.28.1.1
		oRRx1InputPower OBJECT-TYPE
			SYNTAX INTEGER (-1700..300)
			ACCESS read-only
			STATUS mandatory
			DESCRIPTION
				"Optical input power (Range: -17.0...+3.0 dBm).
				Unit 0.01 dBm."
			::= { oRRxEntry 1 }

		
		-- 1.3.6.1.4.1.3715.3.4.28.1.2
		oRRx1InputPowerHiHi OBJECT-TYPE
			SYNTAX INTEGER (-1700..300)
			ACCESS read-write
			STATUS mandatory
			DESCRIPTION
				"Optical input power HIGH alarm limit. Unit 0.01 dBm."
			::= { oRRxEntry 2 }

		
		-- 1.3.6.1.4.1.3715.3.4.28.1.3
		oRRx1InputPowerHi OBJECT-TYPE
			SYNTAX INTEGER (-1700..300)
			ACCESS read-write
			STATUS mandatory
			DESCRIPTION
				"Optical input power HIGH warning limit. Unit 0.01 dBm."
			::= { oRRxEntry 3 }

		
		-- 1.3.6.1.4.1.3715.3.4.28.1.4
		oRRx1InputPowerLo OBJECT-TYPE
			SYNTAX INTEGER (-1700..300)
			ACCESS read-write
			STATUS mandatory
			DESCRIPTION
				"Optical input power LOW warning limit. Unit 0.01 dBm."
			::= { oRRxEntry 4 }

		
		-- 1.3.6.1.4.1.3715.3.4.28.1.5
		oRRx1InputPowerLoLo OBJECT-TYPE
			SYNTAX INTEGER (-1700..300)
			ACCESS read-write
			STATUS mandatory
			DESCRIPTION
				"Optical input power LOW alarm limit. Unit 0.01 dBm."
			::= { oRRxEntry 5 }

		
		-- 1.3.6.1.4.1.3715.3.4.28.1.6
		oRRx1InputPowerDeadband OBJECT-TYPE
			SYNTAX INTEGER (50..500)
			ACCESS read-write
			STATUS mandatory
			DESCRIPTION
				"Optical input power deadband value. Unit 0.01 dBm."
			::= { oRRxEntry 6 }

		
		-- 1.3.6.1.4.1.3715.3.4.28.1.7
		oRRx1CodeMainReserve OBJECT-TYPE
			SYNTAX INTEGER
				{
				codeMain(1),
				codeReserve(2),
				codeUnknown(3)
				}
			ACCESS read-only
			STATUS mandatory
			DESCRIPTION
				"Received main/reserve code:
				1 = Main
				2 = Reserve
				3 = Unknown"
			::= { oRRxEntry 7 }

		
		-- 1.3.6.1.4.1.3715.3.4.28.1.8
		oRRx1CodeNumberRcvd OBJECT-TYPE
			SYNTAX INTEGER (0..999)
			ACCESS read-only
			STATUS mandatory
			DESCRIPTION
				"Received fiber node number code
				0 = Unknown
				1.. 999 Received number"
			::= { oRRxEntry 8 }

		
		-- 1.3.6.1.4.1.3715.3.4.28.1.9
		oRRx1CodeNumberExptd OBJECT-TYPE
			SYNTAX INTEGER (0..999)
			ACCESS read-write
			STATUS mandatory
			DESCRIPTION
				"Expected transmitter number code (1..999)."
			::= { oRRxEntry 9 }

		
		-- 1.3.6.1.4.1.3715.3.4.28.1.10
		oRRx1Mode OBJECT-TYPE
			SYNTAX INTEGER
				{
				modeNormal(1),
				modeSleep(2)
				}
			ACCESS read-write
			STATUS mandatory
			DESCRIPTION
				"Receiver 1 mode:
				1 = Normal mode
				2 = Sleep mode (no alarms, no warnings)"
			::= { oRRxEntry 10 }

		
		-- 1.3.6.1.4.1.3715.3.4.28.1.11
		oRRx1IngressSwitch OBJECT-TYPE
			SYNTAX INTEGER
				{
				att0dB(1),
				att6dB(2),
				att60dB(3)
				}
			ACCESS read-write
			STATUS mandatory
			DESCRIPTION
				"Receiver 1 ingress attenuator state:
				1 = 0 dB
				2 = - 6 dB
				3 = - 60dB (receiver sleep)"
			::= { oRRxEntry 11 }

		
		-- 1.3.6.1.4.1.3715.3.4.28.1.12
		oRRx1OutputLevel OBJECT-TYPE
			SYNTAX INTEGER
				{
				level86dBuV(1),
				level80dBuV(2)
				}
			ACCESS read-write
			STATUS mandatory
			DESCRIPTION
				"Receiver 1 output level setting:
				1 = Output level 86 dBµV
				2 = Output level 80 dBµV"
			::= { oRRxEntry 12 }

		
		-- 1.3.6.1.4.1.3715.3.4.28.1.13
		oRRx2InputPower OBJECT-TYPE
			SYNTAX INTEGER (-1700..300)
			ACCESS read-only
			STATUS mandatory
			DESCRIPTION
				"Optical input power (Range: -17.0...+3.0 dBm).
				Unit 0.01 dBm."
			::= { oRRxEntry 13 }

		
		-- 1.3.6.1.4.1.3715.3.4.28.1.14
		oRRx2InputPowerHiHi OBJECT-TYPE
			SYNTAX INTEGER (-1700..300)
			ACCESS read-write
			STATUS mandatory
			DESCRIPTION
				"Optical input power HIGH alarm limit. Unit 0.01 dBm."
			::= { oRRxEntry 14 }

		
		-- 1.3.6.1.4.1.3715.3.4.28.1.15
		oRRx2InputPowerHi OBJECT-TYPE
			SYNTAX INTEGER (-1700..300)
			ACCESS read-write
			STATUS mandatory
			DESCRIPTION
				"Optical input power HIGH warning limit. Unit 0.01 dBm."
			::= { oRRxEntry 15 }

		
		-- 1.3.6.1.4.1.3715.3.4.28.1.16
		oRRx2InputPowerLo OBJECT-TYPE
			SYNTAX INTEGER (-1700..300)
			ACCESS read-write
			STATUS mandatory
			DESCRIPTION
				"Optical input power LOW warning limit. Unit 0.01 dBm."
			::= { oRRxEntry 16 }

		
		-- 1.3.6.1.4.1.3715.3.4.28.1.17
		oRRx2InputPowerLoLo OBJECT-TYPE
			SYNTAX INTEGER (-1700..300)
			ACCESS read-write
			STATUS mandatory
			DESCRIPTION
				"Optical input power LOW alarm limit. Unit 0.01 dBm."
			::= { oRRxEntry 17 }

		
		-- 1.3.6.1.4.1.3715.3.4.28.1.18
		oRRx2InputPowerDeadband OBJECT-TYPE
			SYNTAX INTEGER (50..500)
			ACCESS read-write
			STATUS mandatory
			DESCRIPTION
				"Optical input power deadband value. Unit 0.01 dBm."
			::= { oRRxEntry 18 }

		
		-- 1.3.6.1.4.1.3715.3.4.28.1.19
		oRRx2CodeMainReserve OBJECT-TYPE
			SYNTAX INTEGER
				{
				codeMain(1),
				codeReserve(2),
				codeUnknown(3)
				}
			ACCESS read-only
			STATUS mandatory
			DESCRIPTION
				"Received main/reserve code:
				1 = Main
				2 = Reserve
				3 = Unknown"
			::= { oRRxEntry 19 }

		
		-- 1.3.6.1.4.1.3715.3.4.28.1.20
		oRRx2CodeNumberRcvd OBJECT-TYPE
			SYNTAX INTEGER (0..999)
			ACCESS read-only
			STATUS mandatory
			DESCRIPTION
				"Received fiber node number code
				0 = Unknown
				1.. 999 Received number"
			::= { oRRxEntry 20 }

		
		-- 1.3.6.1.4.1.3715.3.4.28.1.21
		oRRx2CodeNumberExptd OBJECT-TYPE
			SYNTAX INTEGER (0..999)
			ACCESS read-write
			STATUS mandatory
			DESCRIPTION
				"Expected transmitter number code (1..999)."
			::= { oRRxEntry 21 }

		
		-- 1.3.6.1.4.1.3715.3.4.28.1.22
		oRRx2Mode OBJECT-TYPE
			SYNTAX INTEGER
				{
				modeNormal(1),
				modeSleep(2)
				}
			ACCESS read-write
			STATUS mandatory
			DESCRIPTION
				"Receiver 2 mode:
				1 = Normal mode
				2 = Sleep mode (no alarms, no warnings)"
			::= { oRRxEntry 22 }

		
		-- 1.3.6.1.4.1.3715.3.4.28.1.23
		oRRx2IngresSwitch OBJECT-TYPE
			SYNTAX INTEGER
				{
				att0dB(1),
				att6dB(2),
				att60dB(3)
				}
			ACCESS read-write
			STATUS mandatory
			DESCRIPTION
				"Receiver 2 ingress attenuator state:
				1 = 0 dB
				2 = - 6 dB
				3 = - 60dB (receiver sleep)"
			::= { oRRxEntry 23 }

		
		-- 1.3.6.1.4.1.3715.3.4.28.1.24
		oRRx2OutputLevel OBJECT-TYPE
			SYNTAX INTEGER
				{
				level86dBuV(1),
				level80dBuV(2)
				}
			ACCESS read-write
			STATUS mandatory
			DESCRIPTION
				"Receiver 2 output level setting:
				1 = Output level 86 dBµV
				2 = Output level 80 dBµV"
			::= { oRRxEntry 24 }

		
		-- 1.3.6.1.4.1.3715.3.4.28.1.25
		oRRxCmnMainReserve OBJECT-TYPE
			SYNTAX INTEGER
				{
				codeReserve(1),
				codeMain(2),
				codeUnknown(3)
				}
			ACCESS read-only
			STATUS mandatory
			DESCRIPTION
				"Main-reserve setting:
				1 = Reserve (default inactive) mode
				2 = Main (default active) mode
				3 = Unknown (This value is alway ReadOnly)"
			::= { oRRxEntry 25 }

		
		-- 1.3.6.1.4.1.3715.3.4.28.1.26
		oRRxCmnCodeUsage OBJECT-TYPE
			SYNTAX INTEGER
				{
				lineCodesNotUsed(1),
				lineCodesUsed(2)
				}
			ACCESS read-write
			STATUS mandatory
			DESCRIPTION
				"Use of lines codes (both receivers):
				1 = No line codes, hard cofing of main/reserve mode,
				    no code alarms
				2 = Use line codes for main/reserve and transmitter
				    number detection"
			::= { oRRxEntry 26 }

		
		-- 1.3.6.1.4.1.3715.3.4.28.1.27
		oRRxCmnOutputMode OBJECT-TYPE
			SYNTAX INTEGER
				{
				outputCommon(1),
				outputSeparate(2)
				}
			ACCESS read-write
			STATUS mandatory
			DESCRIPTION
				"Output usage:
				1 = Use common output
				2 = Use separate outputs"
			::= { oRRxEntry 27 }

		
		-- 1.3.6.1.4.1.3715.3.4.28.1.28
		oRRxCmnRedundancyMode OBJECT-TYPE
			SYNTAX INTEGER
				{
				redundancyNone(1),
				redundancyDevice(2),
				redundancyRoute(3)
				}
			ACCESS read-write
			STATUS mandatory
			DESCRIPTION
				"Redundancy mode:
				1 = No redundancy
				2 = Device redundancy
				3 = Channel redundancy"
			::= { oRRxEntry 28 }

		
		-- 1.3.6.1.4.1.3715.3.4.28.1.29
		oRRx1Status OBJECT-TYPE
			SYNTAX INTEGER
				{
				rxNormal(1),
				rxSleeping(2)
				}
			ACCESS read-only
			STATUS mandatory
			DESCRIPTION
				"Receiver 1 status:
				1 = Normal
				2 = Sleeping"
			::= { oRRxEntry 29 }

		
		-- 1.3.6.1.4.1.3715.3.4.28.1.30
		oRRx1InputPowerStatus OBJECT-TYPE
			SYNTAX INTEGER
				{
				powerNormal(1),
				powerHIHI(2),
				powerHI(3),
				powerLO(4),
				powerLOLO(5)
				}
			ACCESS read-only
			STATUS mandatory
			DESCRIPTION
				"Receiver 1 input power status:
				1 = OK
				2 = HIHI
				3 = HI
				4 = LO
				5 = LOLO"
			::= { oRRxEntry 30 }

		
		-- 1.3.6.1.4.1.3715.3.4.28.1.31
		oRRx1PilotStatus OBJECT-TYPE
			SYNTAX INTEGER
				{
				pilotNormal(1),
				pilotFailure(2)
				}
			ACCESS read-only
			STATUS mandatory
			DESCRIPTION
				"Receiver 1 pilot status:
				1 = normal
				2 = pilot failure"
			::= { oRRxEntry 31 }

		
		-- 1.3.6.1.4.1.3715.3.4.28.1.32
		oRRx1CodeStatus OBJECT-TYPE
			SYNTAX INTEGER
				{
				codeNormal(1),
				codeMismatch(2),
				codeInvalid(3),
				codeDisabled(4)
				}
			ACCESS read-only
			STATUS mandatory
			DESCRIPTION
				"Receiver 1 code status:
				codeNormal(1)   = normal
				codeMismatch(2) = code mismatch (expected code not equal to received)
				codeInvalid(3)  = invalid code received (0)
				codeDisabled(4) = code reception is disabled"
			::= { oRRxEntry 32 }

		
		-- 1.3.6.1.4.1.3715.3.4.28.1.33
		oRRx2Status OBJECT-TYPE
			SYNTAX INTEGER
				{
				rxNormal(1),
				rxSleeping(2)
				}
			ACCESS read-only
			STATUS mandatory
			DESCRIPTION
				"Receiver 2 status:
				1 = Active
				2 = Sleeping"
			::= { oRRxEntry 33 }

		
		-- 1.3.6.1.4.1.3715.3.4.28.1.34
		oRRx2InputPowerStatus OBJECT-TYPE
			SYNTAX INTEGER
				{
				powerNormal(1),
				powerHIHI(2),
				powerHI(3),
				powerLO(4),
				powerLOLO(5)
				}
			ACCESS read-only
			STATUS mandatory
			DESCRIPTION
				"Receiver 2 input power status:
				1 = OK
				2 = HIHI
				3 = HI
				4 = LO
				5 = LOLO"
			::= { oRRxEntry 34 }

		
		-- 1.3.6.1.4.1.3715.3.4.28.1.35
		oRRx2PilotStatus OBJECT-TYPE
			SYNTAX INTEGER
				{
				pilotNormal(1),
				pilotFailure(2)
				}
			ACCESS read-only
			STATUS mandatory
			DESCRIPTION
				"Receiver 2 pilot status:
				1 = normal
				2 = pilot failure"
			::= { oRRxEntry 35 }

		
		-- 1.3.6.1.4.1.3715.3.4.28.1.36
		oRRx2CodeStatus OBJECT-TYPE
			SYNTAX INTEGER
				{
				codeNormal(1),
				codeMismatch(2),
				codeInvalid(3),
				codeDisabled(4)
				}
			ACCESS read-only
			STATUS mandatory
			DESCRIPTION
				"Receiver 2 code status:
				codeNormal(1)   = normal
				codeMismatch(2) = code mismatch (expected code not equal to received)
				codeInvalid(3)  = invalid code received (0)
				codeDisabled(4) = code reception is disabled
				"
			::= { oRRxEntry 36 }

		
		-- 1.3.6.1.4.1.3715.3.4.28.1.37
		oRRxCmnLinkStatus OBJECT-TYPE
			SYNTAX INTEGER
				{
				linkNormal(1),
				linkReserve(2)
				}
			ACCESS read-only
			STATUS mandatory
			DESCRIPTION
				"Link status:
				1 = normal
				2 = reserve"
			::= { oRRxEntry 37 }

		
		-- 1.3.6.1.4.1.3715.3.4.28.1.38
		oRRxCmnIngressSwitchStatus OBJECT-TYPE
			SYNTAX INTEGER
				{
				switchNominal(1),
				switchNotNominal(2)
				}
			ACCESS read-only
			STATUS mandatory
			DESCRIPTION
				"Common ingress switch status:
				switchNominal(1)=Both switches are in nominal positions
				switchNotNominal(2)= One or both swicthes are not in nominal position"
			::= { oRRxEntry 38 }

		
		-- 1.3.6.1.4.1.3715.3.4.28.1.39
		oRRxCmnNominalPortControl OBJECT-TYPE
			SYNTAX INTEGER
				{
				returnToNominal(1),
				defineAsNominal(2)
				}
			ACCESS read-write
			STATUS mandatory
			DESCRIPTION
				"This object controls the return path switches 'nominal'
				setting. Any combination of the switch positions can be
				defined as the 'nominal' setting. A reminder alarm
				will be initiated if any of the switches is not in it's
				nominal position.
				
				Set operations:
				1 = returnToNominal, returns all switches to their nominal
				    positions
				2 = defineNominal, stores the current port configuration
				    as the nominal configuration. 
				
				Get operations
				1 = all switches are in their nominal positions
				2 = one or more switches is not in it's nominal position
				
				Note: Immediately after a set (1 or 2), the return value 
				will be 1 meaning that the switches are in their nominal
				positions.
				
				With BKR100 this object is read only. Returned value is
				always 1 (returnToNominal)."
			::= { oRRxEntry 39 }

		
		-- 1.3.6.1.4.1.3715.3.4.28.1.40
		oRRxCmnNotchControl OBJECT-TYPE
			SYNTAX INTEGER
				{
				notchDisable(1),
				notchEnable(2)
				}
			ACCESS read-write
			STATUS mandatory
			DESCRIPTION
				"Control of the 65 MHz notch:
				1(notchDisable) = notch OFF
				2(notchEnable) = notch ON"
			::= { oRRxEntry 40 }

		
		-- 1.3.6.1.4.1.3715.3.4.28.1.41
		oRRx1Gain OBJECT-TYPE
			SYNTAX INTEGER
			ACCESS read-write
			STATUS mandatory
			DESCRIPTION
				"Input 1 gain control value. Unit 0.01 dB."
			::= { oRRxEntry 41 }

		
		-- 1.3.6.1.4.1.3715.3.4.28.1.42
		oRRx1AlcMode OBJECT-TYPE
			SYNTAX INTEGER
				{
				modeManual(1),
				modeAlc(2)
				}
			ACCESS read-write
			STATUS mandatory
			DESCRIPTION
				"Input 1 ALC mode:
				modeManual(1)=manual gain control
				modeAlc(2)   =automatic gain control"
			::= { oRRxEntry 42 }

		
		-- 1.3.6.1.4.1.3715.3.4.28.1.43
		oRRx1AlcStatus OBJECT-TYPE
			SYNTAX INTEGER
				{
				alcNormal(1),
				alcSaturated(2)
				}
			ACCESS read-only
			STATUS mandatory
			DESCRIPTION
				"Input 1 ALC status:
				alcNormal(1)    =ALC operates normally
				alcSaturated(2) =ALC is saturated
				If oRRx1AlcMode is set to modeManual(1), this object always
				returns value alsNormal(1)."
			::= { oRRxEntry 43 }

		
		-- 1.3.6.1.4.1.3715.3.4.28.1.44
		oRRx2Gain OBJECT-TYPE
			SYNTAX INTEGER
			ACCESS read-write
			STATUS mandatory
			DESCRIPTION
				"Input 2 gain control value. Unit 0.01 dB."
			::= { oRRxEntry 44 }

		
		-- 1.3.6.1.4.1.3715.3.4.28.1.47
		oRRxCmnSlope OBJECT-TYPE
			SYNTAX INTEGER
			ACCESS read-write
			STATUS mandatory
			DESCRIPTION
				"Slope control value. Unit 0.01 dB. Common to both inputs."
			::= { oRRxEntry 47 }

		
		-- 1.3.6.1.4.1.3715.3.4.29
		oVA2Table OBJECT-TYPE
			SYNTAX SEQUENCE OF OVA2Entry
			ACCESS not-accessible
			STATUS mandatory
			DESCRIPTION
				"This table contains element specific information
				for Optical Amplifier modules inserted into
				the BK backplane."
			::= { bkModules2 29 }

		
		-- 1.3.6.1.4.1.3715.3.4.29.1
		oVA2Entry OBJECT-TYPE
			SYNTAX OVA2Entry
			ACCESS not-accessible
			STATUS mandatory
			DESCRIPTION
				"Row in Table. Note that index is moduleIndex which is column in 
				the moduleTable defined in TELESTE-COMMON-MIB. Rows in this table
				exist only if there are corresponding rows in the moduleTable."
			INDEX { moduleId }
			::= { oVA2Table 1 }

		
		OVA2Entry ::=
			SEQUENCE { 
				oVa2InputPower
					INTEGER,
				oVa2InputPowerHiHi
					INTEGER,
				oVa2InputPowerHi
					INTEGER,
				oVa2InputPowerLo
					INTEGER,
				oVa2InputPowerLoLo
					INTEGER,
				oVa2InputPowerDeadband
					INTEGER,
				oVa2OutputParamOffset
					INTEGER,
				oVa2OutputParamOffsetHiHi
					INTEGER,
				oVa2OutputParamOffsetHi
					INTEGER,
				oVa2OutputParamOffsetLo
					INTEGER,
				oVa2OutputParamOffsetLoLo
					INTEGER,
				oVa2OutputParamOffsetDeadband
					INTEGER,
				oVa2OutputParamNominal
					INTEGER,
				oVa2OutputParamStepSize
					INTEGER,
				oVa2OutputParamControl
					INTEGER,
				oVa2OutputParamControlMax
					INTEGER,
				oVa2OutputParamControlMin
					INTEGER,
				oVa2OutputControl
					INTEGER,
				oVa2RegulationMode
					INTEGER,
				oVa2SystemInfo
					INTEGER,
				oVa2ReturnLoss
					INTEGER,
				oVa2ReturnLossHiHi
					INTEGER,
				oVa2ReturnLossHi
					INTEGER,
				oVa2ReturnLossLo
					INTEGER,
				oVa2ReturnLossLoLo
					INTEGER,
				oVa2ReturnLossDeadband
					INTEGER,
				oVa2SbsEvaluationMode
					INTEGER,
				oVa2SbsEvaluationStart
					INTEGER,
				oVa2SbsEvaluationTime
					INTEGER,
				oVa2SbsPowerValue
					INTEGER,
				oVa2SystemStatus
					INTEGER,
				oVa2InputPowerStatus
					INTEGER,
				oVa2OutputParamStatus
					INTEGER,
				oVa2ReturnLossStatus
					INTEGER,
				oVa2InputVoltageStatus
					INTEGER,
				oVa2InternalVoltageStatus
					INTEGER,
				oVa2InternalTemperatureStatus
					INTEGER,
				oVa2NumberOfLasers
					INTEGER,
				oVa2StandbyStatus
					INTEGER,
				oVa2LaserCurrentRelStatus
					INTEGER,
				oVa2LaserTecCurrentRelStatus
					INTEGER,
				oVa2LaserTemperatureStatus
					INTEGER,
				oVa2LaserVoltageStatus
					INTEGER,
				oVA2OutputParamLabel
					INTEGER,
				oVA2OutputParamUnit
					INTEGER
			 }

		-- 1.3.6.1.4.1.3715.3.4.29.1.1
		oVa2InputPower OBJECT-TYPE
			SYNTAX INTEGER
			ACCESS read-only
			STATUS mandatory
			DESCRIPTION
				"Optical input power. Unit 0.01 dBm."
			::= { oVA2Entry 1 }

		
		-- 1.3.6.1.4.1.3715.3.4.29.1.2
		oVa2InputPowerHiHi OBJECT-TYPE
			SYNTAX INTEGER (-1000..1000)
			ACCESS read-write
			STATUS mandatory
			DESCRIPTION
				"Optical input power HIGH alarm limit. Unit 0.01 dBm."
			::= { oVA2Entry 2 }

		
		-- 1.3.6.1.4.1.3715.3.4.29.1.3
		oVa2InputPowerHi OBJECT-TYPE
			SYNTAX INTEGER (-1000..1000)
			ACCESS read-write
			STATUS mandatory
			DESCRIPTION
				"Optical input power HIGH warning limit. Unit 0.01 dBm."
			::= { oVA2Entry 3 }

		
		-- 1.3.6.1.4.1.3715.3.4.29.1.4
		oVa2InputPowerLo OBJECT-TYPE
			SYNTAX INTEGER (-1000..1000)
			ACCESS read-write
			STATUS mandatory
			DESCRIPTION
				"Optical input power LOW warning limit. Unit 0.01 dBm."
			::= { oVA2Entry 4 }

		
		-- 1.3.6.1.4.1.3715.3.4.29.1.5
		oVa2InputPowerLoLo OBJECT-TYPE
			SYNTAX INTEGER (-1000..1000)
			ACCESS read-write
			STATUS mandatory
			DESCRIPTION
				"Optical input power LOW alarm limit. Unit 0.01 dBm."
			::= { oVA2Entry 5 }

		
		-- 1.3.6.1.4.1.3715.3.4.29.1.6
		oVa2InputPowerDeadband OBJECT-TYPE
			SYNTAX INTEGER (50..500)
			ACCESS read-write
			STATUS mandatory
			DESCRIPTION
				"Optical input power deadband value. Unit 0.01 dBm."
			::= { oVA2Entry 6 }

		
		-- 1.3.6.1.4.1.3715.3.4.29.1.7
		oVa2OutputParamOffset OBJECT-TYPE
			SYNTAX INTEGER
			ACCESS read-only
			STATUS mandatory
			DESCRIPTION
				"In constant output power mode: Optical output power offset (from target value). Unit 0.01 dBm
				In constant gain mode: Gain offset (from target value). Unit 0.01 dB"
			::= { oVA2Entry 7 }

		
		-- 1.3.6.1.4.1.3715.3.4.29.1.8
		oVa2OutputParamOffsetHiHi OBJECT-TYPE
			SYNTAX INTEGER (-1000..3000)
			ACCESS read-write
			STATUS mandatory
			DESCRIPTION
				"In constant output power mode: Optical output power offset HIHI limit value. Unit 0.01 dBm
				In constant gain mode: Gain offset HIHI limit value. Unit 0.01 dB"
			::= { oVA2Entry 8 }

		
		-- 1.3.6.1.4.1.3715.3.4.29.1.9
		oVa2OutputParamOffsetHi OBJECT-TYPE
			SYNTAX INTEGER (-1000..3000)
			ACCESS read-write
			STATUS mandatory
			DESCRIPTION
				"In constant output power mode: Optical output power offset Hi limit value. Unit 0.01 dBm
				In constant gain mode: Gain offset Hi limit value. Unit 0.01 dB"
			::= { oVA2Entry 9 }

		
		-- 1.3.6.1.4.1.3715.3.4.29.1.10
		oVa2OutputParamOffsetLo OBJECT-TYPE
			SYNTAX INTEGER (-1000..3000)
			ACCESS read-write
			STATUS mandatory
			DESCRIPTION
				"In constant output power mode: Optical output power offset Lo limit value. Unit 0.01 dBm
				In constant gain mode: Gain offset Lo limit value. Unit 0.01 dB"
			::= { oVA2Entry 10 }

		
		-- 1.3.6.1.4.1.3715.3.4.29.1.11
		oVa2OutputParamOffsetLoLo OBJECT-TYPE
			SYNTAX INTEGER (-1000..3000)
			ACCESS read-write
			STATUS mandatory
			DESCRIPTION
				"In constant output power mode: Optical output power offset LOLO limit value. Unit 0.01 dBm
				In constant gain mode: Gain offset LOLO limit value. Unit 0.01 dB"
			::= { oVA2Entry 11 }

		
		-- 1.3.6.1.4.1.3715.3.4.29.1.12
		oVa2OutputParamOffsetDeadband OBJECT-TYPE
			SYNTAX INTEGER (50..500)
			ACCESS read-write
			STATUS mandatory
			DESCRIPTION
				"In constant output power mode: Optical output power offset deadband value. Unit 0.01 dBm
				In constant gain mode: Gain offset deadband value. Unit 0.01 dB"
			::= { oVA2Entry 12 }

		
		-- 1.3.6.1.4.1.3715.3.4.29.1.13
		oVa2OutputParamNominal OBJECT-TYPE
			SYNTAX INTEGER
			ACCESS read-only
			STATUS mandatory
			DESCRIPTION
				"In constant output power mode: Optical output power nominal value. Unit 0.01 dBm
				In constant gain mode: Gain nominal value. Unit 0.01 dB"
			::= { oVA2Entry 13 }

		
		-- 1.3.6.1.4.1.3715.3.4.29.1.14
		oVa2OutputParamStepSize OBJECT-TYPE
			SYNTAX INTEGER
			ACCESS read-only
			STATUS mandatory
			DESCRIPTION
				"In constant output power mode: Optical output power control step size. Unit 0.01 dBm
				In constant gain mode: Gain control step size. Unit 0.01 dB"
			::= { oVA2Entry 14 }

		
		-- 1.3.6.1.4.1.3715.3.4.29.1.15
		oVa2OutputParamControl OBJECT-TYPE
			SYNTAX INTEGER
			ACCESS read-write
			STATUS mandatory
			DESCRIPTION
				"In constant output power mode: Optical output power control value (difference from nominal value). Unit 0.01 dBm
				In constant gain mode: Gain control value (difference from nominal value). Unit 0.01 dB"
			::= { oVA2Entry 15 }

		
		-- 1.3.6.1.4.1.3715.3.4.29.1.16
		oVa2OutputParamControlMax OBJECT-TYPE
			SYNTAX INTEGER
			ACCESS read-only
			STATUS mandatory
			DESCRIPTION
				"In constant output power mode: Optical output power control maximum value. Unit 0.01 dBm
				In constant gain mode: Gain control maximum value. Unit 0.01 dB"
			::= { oVA2Entry 16 }

		
		-- 1.3.6.1.4.1.3715.3.4.29.1.17
		oVa2OutputParamControlMin OBJECT-TYPE
			SYNTAX INTEGER
			ACCESS read-only
			STATUS mandatory
			DESCRIPTION
				"In constant output power mode: Optical output power control minimum value. Unit 0.01 dBm
				In constant gain mode: Gain control minimum value. Unit 0.01 dB"
			::= { oVA2Entry 17 }

		
		-- 1.3.6.1.4.1.3715.3.4.29.1.18
		oVa2OutputControl OBJECT-TYPE
			SYNTAX INTEGER
				{
				outputOn(1),
				outputOff(2)
				}
			ACCESS read-write
			STATUS mandatory
			DESCRIPTION
				"Optical output control:
				outputOn(1) = optical power ON
				outputOff(2) = optical power OFF"
			::= { oVA2Entry 18 }

		
		-- 1.3.6.1.4.1.3715.3.4.29.1.19
		oVa2RegulationMode OBJECT-TYPE
			SYNTAX INTEGER
				{
				modePower(1),
				modeGain(2)
				}
			ACCESS read-write
			STATUS mandatory
			DESCRIPTION
				"Amplifier operating mode:
				modePower(1) = constant output power mode
				modeGain(2) = constant gain mode
				This setting affects the meaning, value and unit meaning of multiple objects
				as described in the deciptions of the respective objects
				"
			::= { oVA2Entry 19 }

		
		-- 1.3.6.1.4.1.3715.3.4.29.1.20
		oVa2SystemInfo OBJECT-TYPE
			SYNTAX INTEGER
			ACCESS read-only
			STATUS mandatory
			DESCRIPTION
				"Additional system info, bitwise encoded.
				Bit 0: SBS features supported 
				Bit 1: External I/Os supported 
				Bit 2: PowerSupply and Fans supported 
				Bit 3: ReturnLoss detection supported 
				Bit 4: Edfa is a HighPower type 
				Bit 5: reserved"
			::= { oVA2Entry 20 }

		
		-- 1.3.6.1.4.1.3715.3.4.29.1.21
		oVa2ReturnLoss OBJECT-TYPE
			SYNTAX INTEGER
			ACCESS read-only
			STATUS mandatory
			DESCRIPTION
				"Measured return loss value. Unit 0.01 dB."
			::= { oVA2Entry 21 }

		
		-- 1.3.6.1.4.1.3715.3.4.29.1.22
		oVa2ReturnLossHiHi OBJECT-TYPE
			SYNTAX INTEGER (0..10000)
			ACCESS read-write
			STATUS mandatory
			DESCRIPTION
				"Return loss HIGH alarm limit. Unit 0.01 dB."
			::= { oVA2Entry 22 }

		
		-- 1.3.6.1.4.1.3715.3.4.29.1.23
		oVa2ReturnLossHi OBJECT-TYPE
			SYNTAX INTEGER (0..10000)
			ACCESS read-write
			STATUS mandatory
			DESCRIPTION
				"Return loss HIGH warning limit. Unit 0.01 dB."
			::= { oVA2Entry 23 }

		
		-- 1.3.6.1.4.1.3715.3.4.29.1.24
		oVa2ReturnLossLo OBJECT-TYPE
			SYNTAX INTEGER (0..10000)
			ACCESS read-write
			STATUS mandatory
			DESCRIPTION
				"Return loss LOW warning limit. Unit 0.01 dB."
			::= { oVA2Entry 24 }

		
		-- 1.3.6.1.4.1.3715.3.4.29.1.25
		oVa2ReturnLossLoLo OBJECT-TYPE
			SYNTAX INTEGER (0..10000)
			ACCESS read-write
			STATUS mandatory
			DESCRIPTION
				"Return loss LOW alarm limit. Unit 0.01 dB."
			::= { oVA2Entry 25 }

		
		-- 1.3.6.1.4.1.3715.3.4.29.1.26
		oVa2ReturnLossDeadband OBJECT-TYPE
			SYNTAX INTEGER (0..10000)
			ACCESS read-write
			STATUS mandatory
			DESCRIPTION
				"Return loss deadband value. Unit 0.01 dB."
			::= { oVA2Entry 26 }

		
		-- 1.3.6.1.4.1.3715.3.4.29.1.27
		oVa2SbsEvaluationMode OBJECT-TYPE
			SYNTAX INTEGER
				{
				modeStandard(1),
				modeFull(2)
				}
			ACCESS read-write
			STATUS mandatory
			DESCRIPTION
				"SBS evaluation mode:
				modeStandard(1) = standard mode
				modeFull(2) = full mode"
			::= { oVA2Entry 27 }

		
		-- 1.3.6.1.4.1.3715.3.4.29.1.28
		oVa2SbsEvaluationStart OBJECT-TYPE
			SYNTAX INTEGER { evaluationStart(1) }
			ACCESS read-write
			STATUS mandatory
			DESCRIPTION
				"Start SBS evaluation. Write only object, value:
				evaluationStart(1) = start SBS evaluation"
			::= { oVA2Entry 28 }

		
		-- 1.3.6.1.4.1.3715.3.4.29.1.29
		oVa2SbsEvaluationTime OBJECT-TYPE
			SYNTAX INTEGER
			ACCESS read-write
			STATUS mandatory
			DESCRIPTION
				"Time of last SBS evaluation. POSIX format."
			::= { oVA2Entry 29 }

		
		-- 1.3.6.1.4.1.3715.3.4.29.1.30
		oVa2SbsPowerValue OBJECT-TYPE
			SYNTAX INTEGER
			ACCESS read-only
			STATUS mandatory
			DESCRIPTION
				"Measured SBS power value. Unit 0.01 dBm."
			::= { oVA2Entry 30 }

		
		-- 1.3.6.1.4.1.3715.3.4.29.1.31
		oVa2SystemStatus OBJECT-TYPE
			SYNTAX INTEGER
				{
				systemOk(1),
				systemAlarm(2),
				systemWarning(3),
				systemNotification(4)
				}
			ACCESS read-only
			STATUS mandatory
			DESCRIPTION
				"1 = System OK
				2 = System alarm
				3 = System warning
				4 = System notification"
			::= { oVA2Entry 31 }

		
		-- 1.3.6.1.4.1.3715.3.4.29.1.32
		oVa2InputPowerStatus OBJECT-TYPE
			SYNTAX INTEGER
				{
				powerNormal(1),
				powerHIHI(2),
				powerHI(3),
				powerLO(4),
				powerLOLO(5)
				}
			ACCESS read-only
			STATUS mandatory
			DESCRIPTION
				"Input power status
				1 = OK
				2 = HIHI
				3 = HI
				4 = LO
				5 = LOLO"
			::= { oVA2Entry 32 }

		
		-- 1.3.6.1.4.1.3715.3.4.29.1.33
		oVa2OutputParamStatus OBJECT-TYPE
			SYNTAX INTEGER
				{
				statusNormal(1),
				statusHIHI(2),
				statusHi(3),
				statusLo(4),
				statusLOLO(5)
				}
			ACCESS read-only
			STATUS mandatory
			DESCRIPTION
				"Optical output power or amplifier gain value status, depends 
				on the amplifier operating mode (constant power vs. gain).
				Status values:
				statusNormal(1) = parameter value is within limits
				statusHIHI(2) = parameter value is above the HIHI limit
				statusHi(3) = parameter value is above the Hi limit
				statusLo(4) = parameter value is below the Lo limit
				statusLOLO(5) = parameter value is below the LOLO limit"
			::= { oVA2Entry 33 }

		
		-- 1.3.6.1.4.1.3715.3.4.29.1.34
		oVa2ReturnLossStatus OBJECT-TYPE
			SYNTAX INTEGER
				{
				returnLossNormal(1),
				returnLossHIHI(2),
				returnLossHI(3),
				returnLossLO(4),
				returnLossLOLO(5)
				}
			ACCESS read-only
			STATUS mandatory
			DESCRIPTION
				"Return loss status
				1 = OK
				2 = HIHI
				3 = HI
				4 = LO
				5 = LOLO"
			::= { oVA2Entry 34 }

		
		-- 1.3.6.1.4.1.3715.3.4.29.1.35
		oVa2InputVoltageStatus OBJECT-TYPE
			SYNTAX INTEGER
				{
				normal(1),
				alarm(2)
				}
			ACCESS read-only
			STATUS mandatory
			DESCRIPTION
				"Module input voltage  status
				normal(1) = voltage is within limits
				alarm(2) = voltage is outside limits"
			::= { oVA2Entry 35 }

		
		-- 1.3.6.1.4.1.3715.3.4.29.1.36
		oVa2InternalVoltageStatus OBJECT-TYPE
			SYNTAX INTEGER
				{
				normal(1),
				alarm(2)
				}
			ACCESS read-only
			STATUS mandatory
			DESCRIPTION
				"Module internal voltage  status
				normal(1) = voltages are within limits
				alarm(2) = one or more voltages are outside limits"
			::= { oVA2Entry 36 }

		
		-- 1.3.6.1.4.1.3715.3.4.29.1.37
		oVa2InternalTemperatureStatus OBJECT-TYPE
			SYNTAX INTEGER
				{
				normal(1),
				alarm(2)
				}
			ACCESS read-only
			STATUS mandatory
			DESCRIPTION
				"Module internal temperature status
				normal(1) = temperature is within limits
				alarm(2) = temperature is outside limits"
			::= { oVA2Entry 37 }

		
		-- 1.3.6.1.4.1.3715.3.4.29.1.38
		oVa2NumberOfLasers OBJECT-TYPE
			SYNTAX INTEGER (1..4)
			ACCESS read-only
			STATUS mandatory
			DESCRIPTION
				"Number of pump lasers."
			::= { oVA2Entry 38 }

		
		-- 1.3.6.1.4.1.3715.3.4.29.1.39
		oVa2StandbyStatus OBJECT-TYPE
			SYNTAX INTEGER
				{
				noStandby(1),
				standby(2)
				}
			ACCESS read-only
			STATUS mandatory
			DESCRIPTION
				"Standby status, values:
				noStandby(1)= active (optical output is on)
				standby(2) = standby (optical output off)"
			::= { oVA2Entry 39 }

		
		-- 1.3.6.1.4.1.3715.3.4.29.1.40
		oVa2LaserCurrentRelStatus OBJECT-TYPE
			SYNTAX INTEGER
				{
				normal(1),
				alarm(2)
				}
			ACCESS read-only
			STATUS mandatory
			DESCRIPTION
				"Laser BIAS current status
				normal(1) = bias current is within limits
				alarm(2) = bias current is outside limits"
			::= { oVA2Entry 40 }

		
		-- 1.3.6.1.4.1.3715.3.4.29.1.41
		oVa2LaserTecCurrentRelStatus OBJECT-TYPE
			SYNTAX INTEGER
				{
				normal(1),
				alarm(2)
				}
			ACCESS read-only
			STATUS mandatory
			DESCRIPTION
				"Laser TEC current status (TEC = thermo electric cooler)
				normal(1) = TEC current is within limits
				alarm(2) = TEC current is outside limits"
			::= { oVA2Entry 41 }

		
		-- 1.3.6.1.4.1.3715.3.4.29.1.42
		oVa2LaserTemperatureStatus OBJECT-TYPE
			SYNTAX INTEGER
				{
				normal(1),
				alarm(2)
				}
			ACCESS read-only
			STATUS mandatory
			DESCRIPTION
				"Laser temperature status
				normal(1) = temperature is within limits
				alarm(2) = temperature is outside limits"
			::= { oVA2Entry 42 }

		
		-- 1.3.6.1.4.1.3715.3.4.29.1.43
		oVa2LaserVoltageStatus OBJECT-TYPE
			SYNTAX INTEGER
				{
				normal(1),
				alarm(2)
				}
			ACCESS read-only
			STATUS mandatory
			DESCRIPTION
				"Laser voltage status
				normal(1) = voltage is within limits
				alarm(2) = voltage is outside limits"
			::= { oVA2Entry 43 }

		
		-- 1.3.6.1.4.1.3715.3.4.29.1.44
		oVA2OutputParamLabel OBJECT-TYPE
			SYNTAX INTEGER
				{
				power(1),
				gain(2)
				}
			ACCESS read-only
			STATUS mandatory
			DESCRIPTION
				"Label for all OutputParam objects. Values:
				power(1) = label is 'power' (amplifier is in constant output power mode)
				gain(2) = label is 'gain' (amplifier is in constant gain mode)"
			::= { oVA2Entry 44 }

		
		-- 1.3.6.1.4.1.3715.3.4.29.1.45
		oVA2OutputParamUnit OBJECT-TYPE
			SYNTAX INTEGER
				{
				dBm(1),
				dB(2)
				}
			ACCESS read-only
			STATUS mandatory
			DESCRIPTION
				"Unit for all OuputParam objects. Values:
				dBm(1) = unit is dBm (amplifier is in constant output power mode)
				dB(2) = unit is dB (amplifier is in constant gain mode)"
			::= { oVA2Entry 45 }

		
		-- 1.3.6.1.4.1.3715.3.4.30
		oVTx2Table OBJECT-TYPE
			SYNTAX SEQUENCE OF OVTx2Entry
			ACCESS not-accessible
			STATUS mandatory
			DESCRIPTION
				"This table contains element specific information
				for Fibre Transmitter (BOT86X)modules inserted into
				the BK backplane."
			::= { bkModules2 30 }

		
		-- 1.3.6.1.4.1.3715.3.4.30.1
		oVTx2Entry OBJECT-TYPE
			SYNTAX OVTx2Entry
			ACCESS not-accessible
			STATUS mandatory
			DESCRIPTION
				"Row in Table. Note that index is moduleIndex which is column in 
				the moduleTable defined in TELESTE-COMMON-MIB. Rows in this table
				exist only if there are corresponding rows in the moduleTable."
			INDEX { moduleId }
			::= { oVTx2Table 1 }

		
		OVTx2Entry ::=
			SEQUENCE { 
				oVTx2OutputPower
					INTEGER,
				oVTx2OutputPowerStatus
					INTEGER,
				oVTx2RfInputPower
					INTEGER,
				oVTx2RfInputPowerStatus
					INTEGER,
				oVTx2Omi
					INTEGER,
				oVTx2OmiStatus
					INTEGER,
				oVTx2RfGain
					INTEGER,
				oVTx2RfGainStatus
					INTEGER,
				oVTx2LaserCurrentRel
					INTEGER,
				oVTx2LaserCurrentRelStatus
					INTEGER,
				oVTx2TecCurrentRel
					INTEGER,
				oVTx2TecCurrentRelStatus
					INTEGER,
				oVTx2LaserTemperatureOffset
					INTEGER,
				oVTx2LaserTemperatureOffsetStatus
					INTEGER,
				oVTx2PowerSupplyStatus
					INTEGER,
				oVTx2InternalVoltageStatus
					INTEGER,
				oVTx2RfInputSignalStatus
					INTEGER,
				oVTx2FanStatus
					INTEGER,
				oVTx2StandbyStatus
					INTEGER,
				oVTx2AgcStatus
					INTEGER,
				oVTx2SbsStatus
					INTEGER,
				oVTx2InternalAlarm
					INTEGER,
				oVTx2RegulationState
					INTEGER,
				oVTx2DeviceModeA
					INTEGER,
				oVTx2DeviceModeB
					INTEGER,
				oVTx2OmiNominal
					INTEGER,
				oVTx2LaserTemperatureNominal
					INTEGER,
				oVTx2LaserFrequencyNominal
					INTEGER,
				oVTx2LaserOperationMode
					INTEGER,
				oVTx2AgcMode
					INTEGER,
				oVTx2CsoRegulation
					INTEGER,
				oVTx2ChannelDistance
					INTEGER,
				oVTx2FiberLength
					INTEGER,
				oVTx2OmiOffset
					INTEGER,
				oVTx2RfGainOffset
					INTEGER,
				oVTx2SlopeOffset
					INTEGER,
				oVTx2LaserFrequencyOffset
					INTEGER,
				oVTx2SbsSuppression
					INTEGER,
				oVTx2SbsSupressionMode
					INTEGER,
				oVTx2SbsFiberType
					INTEGER,
				oVTx2SbsFiberLength
					INTEGER,
				oVTx2OutputPowerRelHiHi
					INTEGER,
				oVTx2OutputPowerRelHi
					INTEGER,
				oVTx2OutputPowerRelLo
					INTEGER,
				oVTx2OutputPowerRelLoLo
					INTEGER,
				oVTx2OutputPowerRelDeadband
					INTEGER,
				oVTx2RfInputPowerHiHi
					INTEGER,
				oVTx2RfInputPowerHi
					INTEGER,
				oVTx2RfInputPowerLo
					INTEGER,
				oVTx2RfInputPowerLoLo
					INTEGER,
				oVTx2RfInputPowerDeadband
					INTEGER,
				oVTx2OmiHiHi
					INTEGER,
				oVTx2OmiHi
					INTEGER,
				oVTx2OmiLo
					INTEGER,
				oVTx2OmiLoLo
					INTEGER,
				oVTx2OmiDeadband
					INTEGER,
				oVTx2RfGainHiHi
					INTEGER,
				oVTx2RfGainHi
					INTEGER,
				oVTx2RfGainLo
					INTEGER,
				oVTx2RfGainLoLo
					INTEGER,
				oVTx2RfGainDeadband
					INTEGER,
				oVTx2LaserCurrentRelHi
					INTEGER,
				oVTx2LaserCurrentRelDeadband
					INTEGER,
				oVTx2TecCurrentRelHiHi
					INTEGER,
				oVTx2TecCurrentRelHi
					INTEGER,
				oVTx2TecCurrentRelDeadband
					INTEGER,
				oVTx2LaserTemperatureOffsetHi
					INTEGER,
				oVTx2LaserTemperatureOffsetLo
					INTEGER,
				oVTx2LaserTemperatureOffsetDeadband
					INTEGER
			 }

		-- 1.3.6.1.4.1.3715.3.4.30.1.1
		oVTx2OutputPower OBJECT-TYPE
			SYNTAX INTEGER
			ACCESS read-only
			STATUS mandatory
			DESCRIPTION
				"Measured optical output power value. Unit 0.01 dBm."
			::= { oVTx2Entry 1 }

		
		-- 1.3.6.1.4.1.3715.3.4.30.1.2
		oVTx2OutputPowerStatus OBJECT-TYPE
			SYNTAX INTEGER
				{
				powerNormal(1),
				powerHIHI(2),
				powerHI(3),
				powerLO(4),
				powerLOLO(5)
				}
			ACCESS read-only
			STATUS mandatory
			DESCRIPTION
				"Optical output power status:
				1 = OK
				2 = HIHI
				3 = HI
				4 = LO
				5 = LOLO"
			::= { oVTx2Entry 2 }

		
		-- 1.3.6.1.4.1.3715.3.4.30.1.3
		oVTx2RfInputPower OBJECT-TYPE
			SYNTAX INTEGER
			ACCESS read-only
			STATUS mandatory
			DESCRIPTION
				"Total RF input power level. Unit 0.01 dBm."
			::= { oVTx2Entry 3 }

		
		-- 1.3.6.1.4.1.3715.3.4.30.1.4
		oVTx2RfInputPowerStatus OBJECT-TYPE
			SYNTAX INTEGER
				{
				levelNormal(1),
				levelHIHI(2),
				levelHI(3),
				levelLO(4),
				levelLOLO(5)
				}
			ACCESS read-only
			STATUS mandatory
			DESCRIPTION
				"Input RF Power status:
				1 = OK
				2 = HIHI
				3 = HI
				4 = LO
				5 = LOLO"
			::= { oVTx2Entry 4 }

		
		-- 1.3.6.1.4.1.3715.3.4.30.1.5
		oVTx2Omi OBJECT-TYPE
			SYNTAX INTEGER
			ACCESS read-only
			STATUS mandatory
			DESCRIPTION
				"Measured relative OMI. Unit 0.01 dB."
			::= { oVTx2Entry 5 }

		
		-- 1.3.6.1.4.1.3715.3.4.30.1.6
		oVTx2OmiStatus OBJECT-TYPE
			SYNTAX INTEGER
				{
				omiNormal(1),
				omiHIHI(2),
				omiHI(3),
				omiLO(4),
				omiLOLO(5)
				}
			ACCESS read-only
			STATUS mandatory
			DESCRIPTION
				"Relative OMI status:
				1 = OK
				2 = HIHI
				3 = HI
				4 = LO
				5 = LOLO"
			::= { oVTx2Entry 6 }

		
		-- 1.3.6.1.4.1.3715.3.4.30.1.7
		oVTx2RfGain OBJECT-TYPE
			SYNTAX INTEGER
			ACCESS read-only
			STATUS mandatory
			DESCRIPTION
				"BC input RF gain control value in APC mode. Unit 0.01 dB."
			::= { oVTx2Entry 7 }

		
		-- 1.3.6.1.4.1.3715.3.4.30.1.8
		oVTx2RfGainStatus OBJECT-TYPE
			SYNTAX INTEGER
				{
				gainNormal(1),
				gainHIHI(2),
				gainHI(3),
				gainLO(4),
				gainLOLO(5)
				}
			ACCESS read-only
			STATUS mandatory
			DESCRIPTION
				"Input RF gain status:
				1 = OK
				2 = HIHI
				3 = HI
				4 = LO
				5 = LOLO"
			::= { oVTx2Entry 8 }

		
		-- 1.3.6.1.4.1.3715.3.4.30.1.9
		oVTx2LaserCurrentRel OBJECT-TYPE
			SYNTAX INTEGER (0..15000)
			ACCESS read-only
			STATUS mandatory
			DESCRIPTION
				"Laser BIAS current value relative to the value at the
				beginning of life (0...150%). Unit 0.01 %."
			::= { oVTx2Entry 9 }

		
		-- 1.3.6.1.4.1.3715.3.4.30.1.10
		oVTx2LaserCurrentRelStatus OBJECT-TYPE
			SYNTAX INTEGER
				{
				currentNormal(1),
				currentHIHI(2),
				currentHI(3),
				currentLO(4),
				currentLOLO(5)
				}
			ACCESS read-only
			STATUS mandatory
			DESCRIPTION
				"Laser bias current status:
				1 = OK
				2 = HIHI
				3 = HI
				4 = LO
				5 = LOLO"
			::= { oVTx2Entry 10 }

		
		-- 1.3.6.1.4.1.3715.3.4.30.1.11
		oVTx2TecCurrentRel OBJECT-TYPE
			SYNTAX INTEGER (-10000..10000)
			ACCESS read-only
			STATUS mandatory
			DESCRIPTION
				"TEC current relative to a max. value (0...100%).
				Unit 0.01 %.
				Cooling = positive value, heating = negative value."
			::= { oVTx2Entry 11 }

		
		-- 1.3.6.1.4.1.3715.3.4.30.1.12
		oVTx2TecCurrentRelStatus OBJECT-TYPE
			SYNTAX INTEGER
				{
				currentNormal(1),
				currentHIHI(2),
				currentHI(3),
				currentLO(4),
				currentLOLO(5)
				}
			ACCESS read-only
			STATUS mandatory
			DESCRIPTION
				"TEC current status:
				1 = OK
				2 = HIHI
				3 = HI
				4 = LO
				5 = LOLO"
			::= { oVTx2Entry 12 }

		
		-- 1.3.6.1.4.1.3715.3.4.30.1.13
		oVTx2LaserTemperatureOffset OBJECT-TYPE
			SYNTAX INTEGER
			ACCESS read-only
			STATUS mandatory
			DESCRIPTION
				"Laser temperature offset from nominal laser temperature.
				Unit 0.01 degC."
			::= { oVTx2Entry 13 }

		
		-- 1.3.6.1.4.1.3715.3.4.30.1.14
		oVTx2LaserTemperatureOffsetStatus OBJECT-TYPE
			SYNTAX INTEGER
				{
				tempNormal(1),
				tempHIHI(2),
				tempHI(3),
				tempLO(4),
				tempLOLO(5)
				}
			ACCESS read-only
			STATUS mandatory
			DESCRIPTION
				"Laser temperature offset status:
				1 = OK
				2 = HIHI
				3 = HI
				4 = LO
				5 = LOLO"
			::= { oVTx2Entry 14 }

		
		-- 1.3.6.1.4.1.3715.3.4.30.1.15
		oVTx2PowerSupplyStatus OBJECT-TYPE
			SYNTAX INTEGER
				{
				psuOk(1),
				psuAlert(2)
				}
			ACCESS read-only
			STATUS mandatory
			DESCRIPTION
				"Power supply status."
			::= { oVTx2Entry 15 }

		
		-- 1.3.6.1.4.1.3715.3.4.30.1.16
		oVTx2InternalVoltageStatus OBJECT-TYPE
			SYNTAX INTEGER
				{
				voltageGood(1),
				voltageBad(2)
				}
			ACCESS read-only
			STATUS mandatory
			DESCRIPTION
				"Internal supply voltage status.
				This is a common status object for all internal voltages."
			::= { oVTx2Entry 16 }

		
		-- 1.3.6.1.4.1.3715.3.4.30.1.17
		oVTx2RfInputSignalStatus OBJECT-TYPE
			SYNTAX INTEGER
				{
				signalOk(1),
				signalLost(2)
				}
			ACCESS read-write
			STATUS mandatory
			::= { oVTx2Entry 17 }

		
		-- 1.3.6.1.4.1.3715.3.4.30.1.18
		oVTx2FanStatus OBJECT-TYPE
			SYNTAX INTEGER
				{
				fanOk(1),
				fanAlert(2)
				}
			ACCESS read-only
			STATUS mandatory
			DESCRIPTION
				"Fan status."
			::= { oVTx2Entry 18 }

		
		-- 1.3.6.1.4.1.3715.3.4.30.1.19
		oVTx2StandbyStatus OBJECT-TYPE
			SYNTAX INTEGER
				{
				noStandby(1),
				standby(2)
				}
			ACCESS read-only
			STATUS mandatory
			DESCRIPTION
				"Standby status, values:
				noStandby(1)= active
				standby(2) = standby"
			::= { oVTx2Entry 19 }

		
		-- 1.3.6.1.4.1.3715.3.4.30.1.20
		oVTx2AgcStatus OBJECT-TYPE
			SYNTAX INTEGER
				{
				agcOk(1),
				agcAlert(2)
				}
			ACCESS read-only
			STATUS mandatory
			DESCRIPTION
				"AGC status."
			::= { oVTx2Entry 20 }

		
		-- 1.3.6.1.4.1.3715.3.4.30.1.21
		oVTx2SbsStatus OBJECT-TYPE
			SYNTAX INTEGER
				{
				sbsOk(1),
				sbsAlarms(2)
				}
			ACCESS read-write
			STATUS mandatory
			DESCRIPTION
				"sbsAlarms(2) if one or more of following conditions
				- SBS 2 GHz/6 GHz level alarm.
				- PLL 2 GHz/6 GHz PLL alarm.
				otherwise sbsOk(1)."
			::= { oVTx2Entry 21 }

		
		-- 1.3.6.1.4.1.3715.3.4.30.1.22
		oVTx2InternalAlarm OBJECT-TYPE
			SYNTAX INTEGER
				{
				alarmNo(1),
				alarmYes(2)
				}
			ACCESS read-write
			STATUS mandatory
			::= { oVTx2Entry 22 }

		
		-- 1.3.6.1.4.1.3715.3.4.30.1.23
		oVTx2RegulationState OBJECT-TYPE
			SYNTAX INTEGER
				{
				rsPout(1),
				rsCSOrough(2),
				rsCSOfine(3),
				rsPilot(4)
				}
			ACCESS read-only
			STATUS mandatory
			::= { oVTx2Entry 23 }

		
		-- 1.3.6.1.4.1.3715.3.4.30.1.24
		oVTx2DeviceModeA OBJECT-TYPE
			SYNTAX INTEGER
			ACCESS read-only
			STATUS mandatory
			DESCRIPTION
				"Bit0: Extended parameter mode used
				Bit1: No Sbs support
				Bit2: Sbs suppression not changeable
				Bit3: No Itu frequency support 
				Bit4: Itu frequency not changeable
				Bit5  PowerSupply and Fans supported 
				Bit6: External I/Os supported
				Bit7: Fiberlength supported
				Bit8: Catv input not supported
				Bit9: Sat input not supported
				Bit10: SAT LNB supply supported
				Bit11: SAT LNB 22kHz supported
				Bit12: Sbs hardware v2 supported
				Bit13: Pilot controlled cso regulation supported"
			::= { oVTx2Entry 24 }

		
		-- 1.3.6.1.4.1.3715.3.4.30.1.25
		oVTx2DeviceModeB OBJECT-TYPE
			SYNTAX INTEGER
			ACCESS read-only
			STATUS mandatory
			DESCRIPTION
				"Bit0: Sbs hardware v3 supported
				Bit1: Sbs frequency mode supported
				Bit1: Sbs suppression mode supported
				Bit2: Internal alarm supported
				Bit3: reserved 
				Bit4: Sbs fiber parameters supported
				"
			::= { oVTx2Entry 25 }

		
		-- 1.3.6.1.4.1.3715.3.4.30.1.26
		oVTx2OmiNominal OBJECT-TYPE
			SYNTAX INTEGER
			ACCESS read-only
			STATUS mandatory
			DESCRIPTION
				"Nominal OMI. Unit 0.01 %."
			::= { oVTx2Entry 26 }

		
		-- 1.3.6.1.4.1.3715.3.4.30.1.27
		oVTx2LaserTemperatureNominal OBJECT-TYPE
			SYNTAX INTEGER
			ACCESS read-only
			STATUS mandatory
			DESCRIPTION
				"Nominal laser temperature. Unit 0.01 degC."
			::= { oVTx2Entry 27 }

		
		-- 1.3.6.1.4.1.3715.3.4.30.1.28
		oVTx2LaserFrequencyNominal OBJECT-TYPE
			SYNTAX INTEGER
			ACCESS read-only
			STATUS mandatory
			DESCRIPTION
				"Nominal laser frequency. Unit 10 MHz."
			::= { oVTx2Entry 28 }

		
		-- 1.3.6.1.4.1.3715.3.4.30.1.29
		oVTx2LaserOperationMode OBJECT-TYPE
			SYNTAX INTEGER
				{
				laserOff(1),
				laserOn(2),
				laserOffIfError(3)
				}
			ACCESS read-write
			STATUS mandatory
			::= { oVTx2Entry 29 }

		
		-- 1.3.6.1.4.1.3715.3.4.30.1.30
		oVTx2AgcMode OBJECT-TYPE
			SYNTAX INTEGER
				{
				agcManual(1),
				agcAuto(2)
				}
			ACCESS read-write
			STATUS mandatory
			DESCRIPTION
				"1: Manual	AGC off
				2: Auto/CW	AGC on, OMI set for unmodulated carriers
				3: reserved - do not use"
			::= { oVTx2Entry 30 }

		
		-- 1.3.6.1.4.1.3715.3.4.30.1.31
		oVTx2CsoRegulation OBJECT-TYPE
			SYNTAX INTEGER
				{
				csoByChannel(1),
				csoByPilot(2)
				}
			ACCESS read-write
			STATUS mandatory
			::= { oVTx2Entry 31 }

		
		-- 1.3.6.1.4.1.3715.3.4.30.1.32
		oVTx2ChannelDistance OBJECT-TYPE
			SYNTAX INTEGER
			ACCESS read-write
			STATUS mandatory
			DESCRIPTION
				"The channel distance, active for oVTx2CsoRegulation 'csoByChannel' (6MHz, 7MHz, 8MHz). Unit 0.01 MHz."
			::= { oVTx2Entry 32 }

		
		-- 1.3.6.1.4.1.3715.3.4.30.1.33
		oVTx2FiberLength OBJECT-TYPE
			SYNTAX INTEGER
			ACCESS read-write
			STATUS mandatory
			DESCRIPTION
				"Connected fiber length, valid for oVTx2DeviceModeA (Bit7: Fiberlength supported). Unit 0.01 km."
			::= { oVTx2Entry 33 }

		
		-- 1.3.6.1.4.1.3715.3.4.30.1.34
		oVTx2OmiOffset OBJECT-TYPE
			SYNTAX INTEGER
			ACCESS read-write
			STATUS mandatory
			DESCRIPTION
				"Optical Modulation Index (relative to nominal omi). Unit 0.01dB."
			::= { oVTx2Entry 34 }

		
		-- 1.3.6.1.4.1.3715.3.4.30.1.35
		oVTx2RfGainOffset OBJECT-TYPE
			SYNTAX INTEGER
			ACCESS read-write
			STATUS mandatory
			DESCRIPTION
				"The RF gain value (relative to nominal gain) Unit 0.01 dB."
			::= { oVTx2Entry 35 }

		
		-- 1.3.6.1.4.1.3715.3.4.30.1.36
		oVTx2SlopeOffset OBJECT-TYPE
			SYNTAX INTEGER
			ACCESS read-write
			STATUS mandatory
			DESCRIPTION
				"Slope (relative to nominal slope). Unit 0.01 dB."
			::= { oVTx2Entry 36 }

		
		-- 1.3.6.1.4.1.3715.3.4.30.1.37
		oVTx2LaserFrequencyOffset OBJECT-TYPE
			SYNTAX INTEGER
			ACCESS read-write
			STATUS mandatory
			DESCRIPTION
				"Laser frequency offset from nominal value. Unit 10 MHz."
			::= { oVTx2Entry 37 }

		
		-- 1.3.6.1.4.1.3715.3.4.30.1.38
		oVTx2SbsSuppression OBJECT-TYPE
			SYNTAX INTEGER
			ACCESS read-write
			STATUS mandatory
			DESCRIPTION
				"The displayed Sbs suppression. This is not equal to the SBS value set inside the device! Unit 0.01dBm."
			::= { oVTx2Entry 38 }

		
		-- 1.3.6.1.4.1.3715.3.4.30.1.39
		oVTx2SbsSupressionMode OBJECT-TYPE
			SYNTAX INTEGER
				{
				standard(1),
				catvOnly(2)
				}
			ACCESS read-write
			STATUS mandatory
			DESCRIPTION
				"SBS suppression mode
				0: Standard
				( ES28: CATV & SAT-IF or SAT-IF only )
				 ES10: -1006 MHz )
				1: CATV only
				( ES28: CATV only; ES10: -862 MHz )
				(Available at NEC-E only if Sbs suppression mode supported)
				Note: changing this value results in a change of parameters 73, 74 and 120. Reread is necessary.
				"
			::= { oVTx2Entry 39 }

		
		-- 1.3.6.1.4.1.3715.3.4.30.1.40
		oVTx2SbsFiberType OBJECT-TYPE
			SYNTAX INTEGER
				{
				singleModeStandard(1),
				singleModeEnhanced(2)
				}
			ACCESS read-write
			STATUS mandatory
			DESCRIPTION
				"Fiber Type:
				0: Standard SMF (Single Mode Fiber)
				1: SBS Enhanced SMF (Single Mode Fiber)
				(Available only if Sbs fiber parameters supported)
				Note: changing this value results in a change of parameters 73, 74 and 120. Reread is necessary."
			::= { oVTx2Entry 40 }

		
		-- 1.3.6.1.4.1.3715.3.4.30.1.41
		oVTx2SbsFiberLength OBJECT-TYPE
			SYNTAX INTEGER
				{
				len10km(1),
				len25km(2),
				len40km(3),
				len65km(4)
				}
			ACCESS read-write
			STATUS mandatory
			DESCRIPTION
				"SBS fiber length
				0: 10km
				1: 25km
				2: 40km
				3: 65km
				(Available only if Sbs fiber parameters supported: See oVTx2DeviceModeB)
				Note: changing this value results in a change of parameters 73, 74 and 120. Reread is necessary.
				"
			::= { oVTx2Entry 41 }

		
		-- 1.3.6.1.4.1.3715.3.4.30.1.42
		oVTx2OutputPowerRelHiHi OBJECT-TYPE
			SYNTAX INTEGER
			ACCESS read-write
			STATUS mandatory
			DESCRIPTION
				"Relative optical output power HIGH alarm limit. Unit 0.01 dB."
			::= { oVTx2Entry 42 }

		
		-- 1.3.6.1.4.1.3715.3.4.30.1.43
		oVTx2OutputPowerRelHi OBJECT-TYPE
			SYNTAX INTEGER
			ACCESS read-write
			STATUS mandatory
			DESCRIPTION
				"Relative optical output power HIGH warning limit. Unit 0.01 dB."
			::= { oVTx2Entry 43 }

		
		-- 1.3.6.1.4.1.3715.3.4.30.1.44
		oVTx2OutputPowerRelLo OBJECT-TYPE
			SYNTAX INTEGER
			ACCESS read-write
			STATUS mandatory
			DESCRIPTION
				"Relative optical output power LOW warning limit. Unit 0.01 dB."
			::= { oVTx2Entry 44 }

		
		-- 1.3.6.1.4.1.3715.3.4.30.1.45
		oVTx2OutputPowerRelLoLo OBJECT-TYPE
			SYNTAX INTEGER
			ACCESS read-write
			STATUS mandatory
			DESCRIPTION
				"Relative optical output power LOW alarm limit. Unit 0.01 dB."
			::= { oVTx2Entry 45 }

		
		-- 1.3.6.1.4.1.3715.3.4.30.1.46
		oVTx2OutputPowerRelDeadband OBJECT-TYPE
			SYNTAX INTEGER
			ACCESS read-write
			STATUS mandatory
			DESCRIPTION
				"Relative optical output power deadband value. Unit 0.01 dB."
			::= { oVTx2Entry 46 }

		
		-- 1.3.6.1.4.1.3715.3.4.30.1.47
		oVTx2RfInputPowerHiHi OBJECT-TYPE
			SYNTAX INTEGER
			ACCESS read-write
			STATUS mandatory
			DESCRIPTION
				"RF input power HIGH alarm limit. Unit 0.01 dBm."
			::= { oVTx2Entry 47 }

		
		-- 1.3.6.1.4.1.3715.3.4.30.1.48
		oVTx2RfInputPowerHi OBJECT-TYPE
			SYNTAX INTEGER
			ACCESS read-write
			STATUS mandatory
			DESCRIPTION
				"RF input power HIGH warning limit. Unit 0.01 dBm."
			::= { oVTx2Entry 48 }

		
		-- 1.3.6.1.4.1.3715.3.4.30.1.49
		oVTx2RfInputPowerLo OBJECT-TYPE
			SYNTAX INTEGER
			ACCESS read-write
			STATUS mandatory
			DESCRIPTION
				"RF input power LOW warning limit. Unit 0.01 dBm."
			::= { oVTx2Entry 49 }

		
		-- 1.3.6.1.4.1.3715.3.4.30.1.50
		oVTx2RfInputPowerLoLo OBJECT-TYPE
			SYNTAX INTEGER
			ACCESS read-write
			STATUS mandatory
			DESCRIPTION
				"RF input power LOW alarm limit. Unit 0.01 dBm."
			::= { oVTx2Entry 50 }

		
		-- 1.3.6.1.4.1.3715.3.4.30.1.51
		oVTx2RfInputPowerDeadband OBJECT-TYPE
			SYNTAX INTEGER
			ACCESS read-write
			STATUS mandatory
			DESCRIPTION
				"RF input power deadband value. Unit 0.01 dB."
			::= { oVTx2Entry 51 }

		
		-- 1.3.6.1.4.1.3715.3.4.30.1.52
		oVTx2OmiHiHi OBJECT-TYPE
			SYNTAX INTEGER
			ACCESS read-write
			STATUS mandatory
			DESCRIPTION
				"Relative OMI HIGH alarm limit. Unit 0.01 dB."
			::= { oVTx2Entry 52 }

		
		-- 1.3.6.1.4.1.3715.3.4.30.1.53
		oVTx2OmiHi OBJECT-TYPE
			SYNTAX INTEGER
			ACCESS read-write
			STATUS mandatory
			DESCRIPTION
				"Relative OMI HIGH warning limit. Unit 0.01 dB."
			::= { oVTx2Entry 53 }

		
		-- 1.3.6.1.4.1.3715.3.4.30.1.54
		oVTx2OmiLo OBJECT-TYPE
			SYNTAX INTEGER
			ACCESS read-write
			STATUS mandatory
			DESCRIPTION
				"Relative OMI LOW warning limit. Unit 0.01 dB."
			::= { oVTx2Entry 54 }

		
		-- 1.3.6.1.4.1.3715.3.4.30.1.55
		oVTx2OmiLoLo OBJECT-TYPE
			SYNTAX INTEGER
			ACCESS read-write
			STATUS mandatory
			DESCRIPTION
				"Relative OMI Low alarm limit. Unit 0.01 dB."
			::= { oVTx2Entry 55 }

		
		-- 1.3.6.1.4.1.3715.3.4.30.1.56
		oVTx2OmiDeadband OBJECT-TYPE
			SYNTAX INTEGER
			ACCESS read-write
			STATUS mandatory
			DESCRIPTION
				"Relative OMI deadband value. Unit 0.01 dB."
			::= { oVTx2Entry 56 }

		
		-- 1.3.6.1.4.1.3715.3.4.30.1.57
		oVTx2RfGainHiHi OBJECT-TYPE
			SYNTAX INTEGER
			ACCESS read-write
			STATUS mandatory
			DESCRIPTION
				"RF gain HIGH alarm limit. Unit 0.01 dB."
			::= { oVTx2Entry 57 }

		
		-- 1.3.6.1.4.1.3715.3.4.30.1.58
		oVTx2RfGainHi OBJECT-TYPE
			SYNTAX INTEGER
			ACCESS read-write
			STATUS mandatory
			DESCRIPTION
				"RF gain HIGH warning limit. Unit 0.01 dB."
			::= { oVTx2Entry 58 }

		
		-- 1.3.6.1.4.1.3715.3.4.30.1.59
		oVTx2RfGainLo OBJECT-TYPE
			SYNTAX INTEGER
			ACCESS read-write
			STATUS mandatory
			DESCRIPTION
				"RF gain LOW warning limit. Unit 0.01 dB."
			::= { oVTx2Entry 59 }

		
		-- 1.3.6.1.4.1.3715.3.4.30.1.60
		oVTx2RfGainLoLo OBJECT-TYPE
			SYNTAX INTEGER
			ACCESS read-write
			STATUS mandatory
			DESCRIPTION
				"RF gain LOW alarm limit. Unit 0.01 dB."
			::= { oVTx2Entry 60 }

		
		-- 1.3.6.1.4.1.3715.3.4.30.1.61
		oVTx2RfGainDeadband OBJECT-TYPE
			SYNTAX INTEGER
			ACCESS read-write
			STATUS mandatory
			DESCRIPTION
				"RF gain deadband value. Unit 0.01 dB."
			::= { oVTx2Entry 61 }

		
		-- 1.3.6.1.4.1.3715.3.4.30.1.62
		oVTx2LaserCurrentRelHi OBJECT-TYPE
			SYNTAX INTEGER (0..15000)
			ACCESS read-write
			STATUS mandatory
			DESCRIPTION
				"Laser current HIGH warning limit. Unit 0.01 %."
			::= { oVTx2Entry 62 }

		
		-- 1.3.6.1.4.1.3715.3.4.30.1.63
		oVTx2LaserCurrentRelDeadband OBJECT-TYPE
			SYNTAX INTEGER (0..15000)
			ACCESS read-write
			STATUS mandatory
			DESCRIPTION
				"Relative laser current deadband value. Unit 0.01 %."
			::= { oVTx2Entry 63 }

		
		-- 1.3.6.1.4.1.3715.3.4.30.1.64
		oVTx2TecCurrentRelHiHi OBJECT-TYPE
			SYNTAX INTEGER (-10000..10000)
			ACCESS read-write
			STATUS mandatory
			DESCRIPTION
				"Relative TEC current HIGH alarm limit. Unit 0.01 %."
			::= { oVTx2Entry 64 }

		
		-- 1.3.6.1.4.1.3715.3.4.30.1.65
		oVTx2TecCurrentRelHi OBJECT-TYPE
			SYNTAX INTEGER (-10000..10000)
			ACCESS read-write
			STATUS mandatory
			DESCRIPTION
				"Relative TEC current HIGH warning limit. Unit 0.01 %."
			::= { oVTx2Entry 65 }

		
		-- 1.3.6.1.4.1.3715.3.4.30.1.66
		oVTx2TecCurrentRelDeadband OBJECT-TYPE
			SYNTAX INTEGER (-10000..10000)
			ACCESS read-write
			STATUS mandatory
			DESCRIPTION
				"Relative TEC current deadband value. Unit 0.01 %."
			::= { oVTx2Entry 66 }

		
		-- 1.3.6.1.4.1.3715.3.4.30.1.67
		oVTx2LaserTemperatureOffsetHi OBJECT-TYPE
			SYNTAX INTEGER
			ACCESS read-write
			STATUS mandatory
			DESCRIPTION
				"Laser temperature offset HIGH warning limit. Unit 0.01 degC."
			::= { oVTx2Entry 67 }

		
		-- 1.3.6.1.4.1.3715.3.4.30.1.68
		oVTx2LaserTemperatureOffsetLo OBJECT-TYPE
			SYNTAX INTEGER
			ACCESS read-write
			STATUS mandatory
			DESCRIPTION
				"Laser temperature offset LOW warning limit. Unit 0.01 degC."
			::= { oVTx2Entry 68 }

		
		-- 1.3.6.1.4.1.3715.3.4.30.1.69
		oVTx2LaserTemperatureOffsetDeadband OBJECT-TYPE
			SYNTAX INTEGER
			ACCESS read-write
			STATUS mandatory
			DESCRIPTION
				"Laser temperature offset deadband value. Unit 0.01 degC."
			::= { oVTx2Entry 69 }

		
		-- 1.3.6.1.4.1.3715.3.4.31
		kplTable OBJECT-TYPE
			SYNTAX SEQUENCE OF KplEntry
			ACCESS not-accessible
			STATUS mandatory
			DESCRIPTION
				"This table contains element specific information
				for Koppler (BKK421) modules inserted into
				the BK backplane."
			::= { bkModules2 31 }

		
		-- 1.3.6.1.4.1.3715.3.4.31.1
		kplEntry OBJECT-TYPE
			SYNTAX KplEntry
			ACCESS not-accessible
			STATUS mandatory
			DESCRIPTION
				"Row in Table. Note that index is moduleIndex which is column in 
				the moduleTable defined in TELESTE-COMMON-MIB. Rows in this table
				exist only if there are corresponding rows in the moduleTable."
			INDEX { moduleId }
			::= { kplTable 1 }

		
		KplEntry ::=
			SEQUENCE { 
				kplGain
					INTEGER,
				kplSlope
					INTEGER,
				kplDetOffset
					INTEGER,
				kplDetRefMode
					INTEGER,
				kplDetRefValue
					INTEGER,
				kplDetOffsetHiHi
					INTEGER,
				kplDetOffsetHi
					INTEGER,
				kplDetOffsetLo
					INTEGER,
				kplDetOffsetLoLo
					INTEGER,
				kplDetOffsetDeadband
					INTEGER,
				kplDetAverageMode
					INTEGER,
				kplRfLevelStatus
					INTEGER,
				kplTemperatureStatus
					INTEGER,
				kplGainS1
					INTEGER,
				kplSlopeS1
					INTEGER,
				kplGainS2
					INTEGER,
				kplSlopeS2
					INTEGER,
				kplGainS3
					INTEGER,
				kplSlopeS3
					INTEGER,
				kplGainS4
					INTEGER,
				kplSlopeS4
					INTEGER,
				kplDet2Offset
					INTEGER,
				kplDet2RefMode
					INTEGER,
				kplDet2RefValue
					INTEGER,
				kplDet2OffsetHiHi
					INTEGER,
				kplDet2OffsetHi
					INTEGER,
				kplDet2OffsetLo
					INTEGER,
				kplDet2OffsetLoLo
					INTEGER,
				kplDet2OffsetDeadband
					INTEGER,
				kplRfLevel2Status
					INTEGER,
				kplDet3Offset
					INTEGER,
				kplDet3RefMode
					INTEGER,
				kplDet3RefValue
					INTEGER,
				kplDet3OffsetHiHi
					INTEGER,
				kplDet3OffsetHi
					INTEGER,
				kplDet3OffsetLo
					INTEGER,
				kplDet3OffsetLoLo
					INTEGER,
				kplDet3OffsetDeadband
					INTEGER,
				kplRfLevel3Status
					INTEGER
			 }

		-- 1.3.6.1.4.1.3715.3.4.31.1.1
		kplGain OBJECT-TYPE
			SYNTAX INTEGER (-2000..0)
			ACCESS read-write
			STATUS mandatory
			DESCRIPTION
				"Gain control value (main input). HF5 input in BKK421.
				Unit 0.01 dB. Control range is -20...0 dB (value range -2000...0)."
			::= { kplEntry 1 }

		
		-- 1.3.6.1.4.1.3715.3.4.31.1.2
		kplSlope OBJECT-TYPE
			SYNTAX INTEGER (0..800)
			ACCESS read-write
			STATUS mandatory
			DESCRIPTION
				"Slope control value (main input). HF5 input in BKK421.
				Unit 0.01 dB. Control range is 0....+ 8 dB ( value range 0...800).
				"
			::= { kplEntry 2 }

		
		-- 1.3.6.1.4.1.3715.3.4.31.1.3
		kplDetOffset OBJECT-TYPE
			SYNTAX INTEGER (-10000..10000)
			ACCESS read-only
			STATUS mandatory
			DESCRIPTION
				"RF detector offset value. Unit 0.01 dB."
			::= { kplEntry 3 }

		
		-- 1.3.6.1.4.1.3715.3.4.31.1.4
		kplDetRefMode OBJECT-TYPE
			SYNTAX INTEGER
				{
				refFactory(1),
				refUser(2)
				}
			ACCESS read-write
			STATUS mandatory
			DESCRIPTION
				"RF detector reference mode.
				1 = factory
				2 = user"
			::= { kplEntry 4 }

		
		-- 1.3.6.1.4.1.3715.3.4.31.1.5
		kplDetRefValue OBJECT-TYPE
			SYNTAX INTEGER
			ACCESS read-write
			STATUS mandatory
			DESCRIPTION
				"Nominal RF detector value. Unit 0.01 dBµV."
			::= { kplEntry 5 }

		
		-- 1.3.6.1.4.1.3715.3.4.31.1.6
		kplDetOffsetHiHi OBJECT-TYPE
			SYNTAX INTEGER (0..10000)
			ACCESS read-write
			STATUS mandatory
			DESCRIPTION
				"RF detector HIGH ALARM limit. Unit 0.01 dB."
			::= { kplEntry 6 }

		
		-- 1.3.6.1.4.1.3715.3.4.31.1.7
		kplDetOffsetHi OBJECT-TYPE
			SYNTAX INTEGER (0..10000)
			ACCESS read-write
			STATUS mandatory
			DESCRIPTION
				"RF detector HIGH WARNING limit. Unit 0.01 dB."
			::= { kplEntry 7 }

		
		-- 1.3.6.1.4.1.3715.3.4.31.1.8
		kplDetOffsetLo OBJECT-TYPE
			SYNTAX INTEGER (-10000..0)
			ACCESS read-write
			STATUS mandatory
			DESCRIPTION
				"RF detector LOW WARNING limit. Unit 0.01 dB."
			::= { kplEntry 8 }

		
		-- 1.3.6.1.4.1.3715.3.4.31.1.9
		kplDetOffsetLoLo OBJECT-TYPE
			SYNTAX INTEGER (-10000..0)
			ACCESS read-write
			STATUS mandatory
			DESCRIPTION
				"RF detector LOW ALARM limit. Unit 0.01 dB."
			::= { kplEntry 9 }

		
		-- 1.3.6.1.4.1.3715.3.4.31.1.10
		kplDetOffsetDeadband OBJECT-TYPE
			SYNTAX INTEGER (50..1000)
			ACCESS read-write
			STATUS mandatory
			DESCRIPTION
				"RF detector deadband value. Unit 0.01 dB."
			::= { kplEntry 10 }

		
		-- 1.3.6.1.4.1.3715.3.4.31.1.11
		kplDetAverageMode OBJECT-TYPE
			SYNTAX INTEGER
				{
				modeOff(1),
				modeOn(2)
				}
			ACCESS read-write
			STATUS mandatory
			DESCRIPTION
				"RF detector averaging status:
				1 = averaging off
				2 = averaging on"
			::= { kplEntry 11 }

		
		-- 1.3.6.1.4.1.3715.3.4.31.1.13
		kplRfLevelStatus OBJECT-TYPE
			SYNTAX INTEGER
				{
				levelNormal(1),
				levelHIHI(2),
				levelHI(3),
				levelLO(4),
				levelLOLO(5)
				}
			ACCESS read-only
			STATUS mandatory
			DESCRIPTION
				"RF detector level status
				1 = OK
				2 = HIHI
				3 = HI
				4 = LO
				5 = LOLO"
			::= { kplEntry 13 }

		
		-- 1.3.6.1.4.1.3715.3.4.31.1.14
		kplTemperatureStatus OBJECT-TYPE
			SYNTAX INTEGER
				{
				tempNormal(1),
				tempHIHI(2),
				tempHI(3),
				tempLO(4),
				tempLOLO(5)
				}
			ACCESS read-only
			STATUS mandatory
			DESCRIPTION
				"Module temperature Status.
				1 = OK
				2 = HIHI
				3 = HI
				4 = LO
				5 = LOLO"
			::= { kplEntry 14 }

		
		-- 1.3.6.1.4.1.3715.3.4.31.1.20
		kplGainS1 OBJECT-TYPE
			SYNTAX INTEGER (-2000..0)
			ACCESS read-write
			STATUS mandatory
			DESCRIPTION
				"Gain control value of secondary input 1. HF7-1 input in BKK421.
				Unit 0.01 dB. Control range is -20...0 dB (value range -2000...0).."
			::= { kplEntry 20 }

		
		-- 1.3.6.1.4.1.3715.3.4.31.1.21
		kplSlopeS1 OBJECT-TYPE
			SYNTAX INTEGER (0..800)
			ACCESS read-write
			STATUS mandatory
			DESCRIPTION
				"Slope control value of secondary input 1. HF7-1 input in BKK421.
				Unit 0.01 dB. Control range is 0....+ 8 dB ( value range 0...800)."
			::= { kplEntry 21 }

		
		-- 1.3.6.1.4.1.3715.3.4.31.1.22
		kplGainS2 OBJECT-TYPE
			SYNTAX INTEGER (-2000..0)
			ACCESS read-write
			STATUS mandatory
			DESCRIPTION
				"Gain control value of secondary input 2. HF7-2 input in BKK421.
				Unit 0.01 dB. Control range is -20...0 dB (value range -2000...0)."
			::= { kplEntry 22 }

		
		-- 1.3.6.1.4.1.3715.3.4.31.1.23
		kplSlopeS2 OBJECT-TYPE
			SYNTAX INTEGER (0..800)
			ACCESS read-write
			STATUS mandatory
			DESCRIPTION
				"Slope control value of secondary input 2. HF7-2 input in BKK421.
				Unit 0.01 dB. Control range is 0....+ 8 dB ( value range 0...800)."
			::= { kplEntry 23 }

		
		-- 1.3.6.1.4.1.3715.3.4.31.1.24
		kplGainS3 OBJECT-TYPE
			SYNTAX INTEGER (-2000..0)
			ACCESS read-write
			STATUS mandatory
			DESCRIPTION
				"Gain control value of secondary input 3. HF7-3 input in BKK421.
				Unit 0.01 dB. Control range is -20...0 dB (value range -2000...0)."
			::= { kplEntry 24 }

		
		-- 1.3.6.1.4.1.3715.3.4.31.1.25
		kplSlopeS3 OBJECT-TYPE
			SYNTAX INTEGER (0..800)
			ACCESS read-write
			STATUS mandatory
			DESCRIPTION
				"Slope control value of secondary input 3. HF7-3 input in BKK421.
				Unit 0.01 dB. Control range is 0....+ 8 dB ( value range 0...800)."
			::= { kplEntry 25 }

		
		-- 1.3.6.1.4.1.3715.3.4.31.1.26
		kplGainS4 OBJECT-TYPE
			SYNTAX INTEGER (-2000..0)
			ACCESS read-write
			STATUS mandatory
			DESCRIPTION
				"Gain control value of secondary input 4. HF8 input in BKK421.
				Unit 0.01 dB. Control range is -20...0 dB (value range -2000...0)."
			::= { kplEntry 26 }

		
		-- 1.3.6.1.4.1.3715.3.4.31.1.27
		kplSlopeS4 OBJECT-TYPE
			SYNTAX INTEGER (0..800)
			ACCESS read-write
			STATUS mandatory
			DESCRIPTION
				"Slope control value of secondary input 4. HF8 input in BKK421.
				Unit 0.01 dB. Control range is 0....+ 8 dB ( value range 0...800)."
			::= { kplEntry 27 }

		
		-- 1.3.6.1.4.1.3715.3.4.31.1.28
		kplDet2Offset OBJECT-TYPE
			SYNTAX INTEGER (-10000..10000)
			ACCESS read-only
			STATUS mandatory
			DESCRIPTION
				"Second RF detector offset value. Input HF5 for BKK422. Unit 0.01 dB."
			::= { kplEntry 28 }

		
		-- 1.3.6.1.4.1.3715.3.4.31.1.29
		kplDet2RefMode OBJECT-TYPE
			SYNTAX INTEGER
				{
				refFactory(1),
				refUser(2)
				}
			ACCESS read-write
			STATUS mandatory
			DESCRIPTION
				"Second RF detector reference mode. Input HF5 for BKK422.
				1 = factory
				2 = user"
			::= { kplEntry 29 }

		
		-- 1.3.6.1.4.1.3715.3.4.31.1.30
		kplDet2RefValue OBJECT-TYPE
			SYNTAX INTEGER
			ACCESS read-write
			STATUS mandatory
			DESCRIPTION
				"Nominal second RF detector value. Input HF5 for BKK422. Unit 0.01 dBµV."
			::= { kplEntry 30 }

		
		-- 1.3.6.1.4.1.3715.3.4.31.1.31
		kplDet2OffsetHiHi OBJECT-TYPE
			SYNTAX INTEGER (0..10000)
			ACCESS read-write
			STATUS mandatory
			DESCRIPTION
				"Second RF detector HIGH ALARM limit. Input HF5 for BKK422. Unit 0.01 dB."
			::= { kplEntry 31 }

		
		-- 1.3.6.1.4.1.3715.3.4.31.1.32
		kplDet2OffsetHi OBJECT-TYPE
			SYNTAX INTEGER (0..10000)
			ACCESS read-write
			STATUS mandatory
			DESCRIPTION
				"Second RF detector HIGH WARNING limit. Input HF5 for BKK422. Unit 0.01 dB."
			::= { kplEntry 32 }

		
		-- 1.3.6.1.4.1.3715.3.4.31.1.33
		kplDet2OffsetLo OBJECT-TYPE
			SYNTAX INTEGER (-10000..0)
			ACCESS read-write
			STATUS mandatory
			DESCRIPTION
				"Second RF detector LOW WARNING limit. Input HF5 for BKK422. Unit 0.01 dB."
			::= { kplEntry 33 }

		
		-- 1.3.6.1.4.1.3715.3.4.31.1.34
		kplDet2OffsetLoLo OBJECT-TYPE
			SYNTAX INTEGER (-10000..0)
			ACCESS read-write
			STATUS mandatory
			DESCRIPTION
				"Second RF detector LOW ALARM limit. Input HF5 for BKK422. Unit 0.01 dB."
			::= { kplEntry 34 }

		
		-- 1.3.6.1.4.1.3715.3.4.31.1.35
		kplDet2OffsetDeadband OBJECT-TYPE
			SYNTAX INTEGER (50..1000)
			ACCESS read-write
			STATUS mandatory
			DESCRIPTION
				"Second RF detector deadband value. Input HF5 for BKK422. Unit 0.01 dB."
			::= { kplEntry 35 }

		
		-- 1.3.6.1.4.1.3715.3.4.31.1.36
		kplRfLevel2Status OBJECT-TYPE
			SYNTAX INTEGER
				{
				levelNormal(1),
				levelHIHI(2),
				levelHI(3),
				levelLO(4),
				levelLOLO(5)
				}
			ACCESS read-only
			STATUS mandatory
			DESCRIPTION
				"Second RF detector level status. Input HF5 for BKK422.
				1 = OK
				2 = HIHI
				3 = HI
				4 = LO
				5 = LOLO"
			::= { kplEntry 36 }

		
		-- 1.3.6.1.4.1.3715.3.4.31.1.37
		kplDet3Offset OBJECT-TYPE
			SYNTAX INTEGER (-10000..10000)
			ACCESS read-only
			STATUS mandatory
			DESCRIPTION
				"Third RF detector offset value. Inputs HF7-1 + HF7-2 + HF7-3 + HF8 for BKK422. Unit 0.01 dB."
			::= { kplEntry 37 }

		
		-- 1.3.6.1.4.1.3715.3.4.31.1.38
		kplDet3RefMode OBJECT-TYPE
			SYNTAX INTEGER
				{
				refFactory(1),
				refUser(2)
				}
			ACCESS read-write
			STATUS mandatory
			DESCRIPTION
				"Third RF detector reference mode. Inputs HF7-1 + HF7-2 + HF7-3 + HF8 for BKK422.
				1 = factory
				2 = user"
			::= { kplEntry 38 }

		
		-- 1.3.6.1.4.1.3715.3.4.31.1.39
		kplDet3RefValue OBJECT-TYPE
			SYNTAX INTEGER
			ACCESS read-write
			STATUS mandatory
			DESCRIPTION
				"Nominal third RF detector value. Inputs HF7-1 + HF7-2 + HF7-3 + HF8 for BKK422. Unit 0.01 dBµV."
			::= { kplEntry 39 }

		
		-- 1.3.6.1.4.1.3715.3.4.31.1.40
		kplDet3OffsetHiHi OBJECT-TYPE
			SYNTAX INTEGER (0..10000)
			ACCESS read-write
			STATUS mandatory
			DESCRIPTION
				"Third RF detector HIGH ALARM limit. Inputs HF7-1 + HF7-2 + HF7-3 + HF8 for BKK422. Unit 0.01 dB."
			::= { kplEntry 40 }

		
		-- 1.3.6.1.4.1.3715.3.4.31.1.41
		kplDet3OffsetHi OBJECT-TYPE
			SYNTAX INTEGER (0..10000)
			ACCESS read-write
			STATUS mandatory
			DESCRIPTION
				"Third RF detector HIGH WARNING limit. Inputs HF7-1 + HF7-2 + HF7-3 + HF8 for BKK422. Unit 0.01 dB."
			::= { kplEntry 41 }

		
		-- 1.3.6.1.4.1.3715.3.4.31.1.42
		kplDet3OffsetLo OBJECT-TYPE
			SYNTAX INTEGER (-10000..0)
			ACCESS read-write
			STATUS mandatory
			DESCRIPTION
				"Third RF detector LOW WARNING limit. Inputs HF7-1 + HF7-2 + HF7-3 + HF8 for BKK422. Unit 0.01 dB."
			::= { kplEntry 42 }

		
		-- 1.3.6.1.4.1.3715.3.4.31.1.43
		kplDet3OffsetLoLo OBJECT-TYPE
			SYNTAX INTEGER (-10000..0)
			ACCESS read-write
			STATUS mandatory
			DESCRIPTION
				"Third RF detector LOW ALARM limit. Inputs HF7-1 + HF7-2 + HF7-3 + HF8 for BKK422. Unit 0.01 dB."
			::= { kplEntry 43 }

		
		-- 1.3.6.1.4.1.3715.3.4.31.1.44
		kplDet3OffsetDeadband OBJECT-TYPE
			SYNTAX INTEGER (50..1000)
			ACCESS read-write
			STATUS mandatory
			DESCRIPTION
				"Third RF detector deadband value. Inputs HF7-1 + HF7-2 + HF7-3 + HF8 for BKK422. Unit 0.01 dB."
			::= { kplEntry 44 }

		
		-- 1.3.6.1.4.1.3715.3.4.31.1.45
		kplRfLevel3Status OBJECT-TYPE
			SYNTAX INTEGER
				{
				levelNormal(1),
				levelHIHI(2),
				levelHI(3),
				levelLO(4),
				levelLOLO(5)
				}
			ACCESS read-only
			STATUS mandatory
			DESCRIPTION
				"Third RF detector level status. Inputs HF7-1 + HF7-2 + HF7-3 + HF8 for BKK422.
				1 = OK
				2 = HIHI
				3 = HI
				4 = LO
				5 = LOLO"
			::= { kplEntry 45 }

		
	
	END

--
-- TELESTE-BK2-MIB.mib
--
