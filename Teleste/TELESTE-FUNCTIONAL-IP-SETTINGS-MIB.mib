--
-- TELESTE-FUNCTIONAL-IP-SETTINGS-MIB.mib
-- MIB generated by MG-SOFT Visual MIB Builder 2013 (64-bit) Version 9.0  Build 760
-- Tuesday, June 14, 2016 at 09:22:34
--

-- ****************************************************************************
-- Copyright (c) 2003-2014 by:
-- 
-- Teleste Corporation
-- Seponkatu 1
-- FIN-20660 Littoinen, Finland
-- tel. +358 2 2605 611
-- url: http://www.teleste.com
-- 
-- Module Name: TELESTE-FUNCTIONAL-IP-SETTINGS-MIB
-- 
-- Description: MIB module describing IP related objects for a interface.
-- 
-- Revision History:
-- -----------------
-- 2, 14.6.2016, Sami Kuusisto
-- - Added snmp community settings OIDs: snmpGetCommunity and snmpSetCommunity.
-- - Added ipLinkStatus.
-- 
-- 1, 8.12.2014, Sami Kuusisto
-- - Initial version
-- 
-- ****************************************************************************

	TELESTE-FUNCTIONAL-IP-SETTINGS-MIB DEFINITIONS ::= BEGIN
 
		IMPORTS
			OBJECT-TYPE			
				FROM RFC-1212			
			IpAddress			
				FROM RFC1155-SMI			
			functionalModuleId			
				FROM TELESTE-FUNCTIONAL-MODULE-MIB			
			functional			
				FROM TELESTE-ROOT-MIB;
	
	
	
--
-- Node definitions
--
	
		-- 1.3.6.1.4.1.3715.100.98
		ipSettings OBJECT IDENTIFIER ::= { functional 98 }

		
		-- 1.3.6.1.4.1.3715.100.98.3
		ipTable OBJECT-TYPE
			SYNTAX SEQUENCE OF IpEntry
			ACCESS not-accessible
			STATUS mandatory
			::= { ipSettings 3 }

		
		-- 1.3.6.1.4.1.3715.100.98.3.1
		ipEntry OBJECT-TYPE
			SYNTAX IpEntry
			ACCESS not-accessible
			STATUS mandatory
			INDEX { functionalModuleId }
			::= { ipTable 1 }

		
		IpEntry ::=
			SEQUENCE { 
				ipAddress
					IpAddress,
				ipNetMask
					IpAddress,
				ipGateway
					IpAddress,
				ipAddressConfigurationMode
					INTEGER,
				ipLinkStatus
					INTEGER
			 }

		-- 1.3.6.1.4.1.3715.100.98.3.1.1
		ipAddress OBJECT-TYPE
			SYNTAX IpAddress
			ACCESS read-write
			STATUS mandatory
			DESCRIPTION
				"Interface IP address."
			::= { ipEntry 1 }

		
		-- 1.3.6.1.4.1.3715.100.98.3.1.2
		ipNetMask OBJECT-TYPE
			SYNTAX IpAddress
			ACCESS read-write
			STATUS mandatory
			DESCRIPTION
				"Netmask of interface."
			::= { ipEntry 2 }

		
		-- 1.3.6.1.4.1.3715.100.98.3.1.3
		ipGateway OBJECT-TYPE
			SYNTAX IpAddress
			ACCESS read-write
			STATUS mandatory
			DESCRIPTION
				"Gateway address of interface."
			::= { ipEntry 3 }

		
		-- 1.3.6.1.4.1.3715.100.98.3.1.4
		ipAddressConfigurationMode OBJECT-TYPE
			SYNTAX INTEGER
				{
				manual(1),
				dhcp(2)
				}
			ACCESS read-write
			STATUS mandatory
			DESCRIPTION
				"IP addressing mode.
				1 = manual / static
				2 = DHCP / AutoIP"
			::= { ipEntry 4 }

		
		-- 1.3.6.1.4.1.3715.100.98.3.1.5
		ipLinkStatus OBJECT-TYPE
			SYNTAX INTEGER
			ACCESS read-only
			STATUS mandatory
			DESCRIPTION
				"Link status as bit field: 0bABCDEFGH
				A: 1: link up, 0: link down
				B: 1: full duplex, 0: half duplex
				C: 1: IP addresses ok (static always, dhcp/autoIP: when addresses received), 0: IP address unavailable (dhcp/autoip)
				D: reserved for future purposes
				EFGH: link speed: 0000: N/A, 0001: unknown, 0010: other, 0011: 19200 bps, 0100: 38400 bps, 0101: 115200 bps, 0110: 10 Mbps, 0111: 100 Mbps, 1000-1111: reserved for future purposes "
			::= { ipEntry 5 }

		
		-- 1.3.6.1.4.1.3715.100.98.4
		snmpGetCommunity OBJECT-TYPE
			SYNTAX OCTET STRING
			ACCESS read-write
			STATUS mandatory
			DESCRIPTION
				"The community name that is allowed for GET requests.
				Maximum length of get community is device dependant. Typically 16 characters."
			::= { ipSettings 4 }

		
		-- 1.3.6.1.4.1.3715.100.98.5
		snmpSetCommunity OBJECT-TYPE
			SYNTAX OCTET STRING
			ACCESS read-write
			STATUS mandatory
			DESCRIPTION
				"The community name that is allowed for SET and GET requests.
				Maximum length of set community is device dependant. Typically 16 characters."
			::= { ipSettings 5 }

		
	
	END

--
-- TELESTE-FUNCTIONAL-IP-SETTINGS-MIB.mib
--
