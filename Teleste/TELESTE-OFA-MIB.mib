--
-- TELESTE-OFA-MIB.mib
-- MIB generated by MG-SOFT Visual MIB Builder 2021 (64-bit) Version 15.00  Build 1510
-- Friday, November 11, 2022 at 12:47:54
--

-- ****************************************************************************
-- Copyright (c) 2018 by:
-- 
-- Teleste Corporation
-- Telestenkatu 1
-- FIN-20660 Littoinen, Finland
-- tel. +358 2 2605 611
-- url: http://www.teleste.com
-- 
-- Module Name:   TELESTE-OFA-MIB
-- 
-- Description:   MIB module describing Teleste OFA series specific objects
-- 
-- Revision history:
-- Rev, YYYY-MM-DD, Authors
-- -----------------
-- 4, 2022-11-11, Sami Kuusisto
-- - Added gen2 OIDs.
-- 
-- 4, 2019-11-01, Sami Kuusisto
-- - Changed ofa73xOutputAttenuation scale from 0.01 dB to 0.1 dB.
-- 
-- 3, 2019-08-19, Sami Kuusisto and Rainer Salminen
-- - Changed ofaPSUStatus enumeration (and meaning).
-- 
-- 2, 2019-06-03, Sami Kuusisto
-- - Added OFA731, OFA733 and OFA737 W, S and WS sysOIDs.
-- 
-- 1, 2018-12-11, Sami Kuusisto and Rainer Salminen
-- - Initial version.
-- 
-- 
-- ****************************************************************************
-- 

	TELESTE-OFA-MIB DEFINITIONS ::= BEGIN
 
		IMPORTS
			OBJECT-TYPE			
				FROM RFC-1212			
			ofa			
				FROM TELESTE-ROOT-MIB;
	
	
	
--
-- Node definitions
--
	
		-- 1.3.6.1.4.1.3715.21.1
		ofaPSU OBJECT IDENTIFIER ::= { ofa 1 }

		
		-- 1.3.6.1.4.1.3715.21.1.1
		ofaPSUCount OBJECT-TYPE
			SYNTAX INTEGER
			ACCESS read-write
			STATUS mandatory
			DESCRIPTION
				"Number of detected power supplies."
			::= { ofaPSU 1 }

		
		-- 1.3.6.1.4.1.3715.21.1.2
		ofaPSUStatus OBJECT-TYPE
			SYNTAX INTEGER
				{
				normal(1),
				fault(2)
				}
			ACCESS read-only
			STATUS mandatory
			DESCRIPTION
				"Current status of power supplies.
				
				1: Power supplies working ok.
				2: Power supply failure.
				"
			::= { ofaPSU 2 }

		
-- OFA731 gen1 sysOID
		-- 1.3.6.1.4.1.3715.21.731
		ofa731 OBJECT IDENTIFIER ::= { ofa 731 }

		
		-- 1.3.6.1.4.1.3715.21.731.1
		ofa731OutputAttenuation OBJECT-TYPE
			SYNTAX INTEGER
			ACCESS read-write
			STATUS mandatory
			DESCRIPTION
				"Output attenuation.
				
				Unit 0.1 dB."
			::= { ofa731 1 }

		
-- OFA731 gen2 sysOID
		-- 1.3.6.1.4.1.3715.21.731.2
		ofa731-gen2 OBJECT IDENTIFIER ::= { ofa731 2 }

		
-- OFA731S gen1 sysOID
		-- 1.3.6.1.4.1.3715.21.731.115
		ofa731s OBJECT IDENTIFIER ::= { ofa731 115 }

		
-- OFA731S gen2 sysOID
		-- 1.3.6.1.4.1.3715.21.731.115.2
		ofa731s-gen2 OBJECT IDENTIFIER ::= { ofa731s 2 }

		
-- OFA731W gen1 sysOID
		-- 1.3.6.1.4.1.3715.21.731.119
		ofa731w OBJECT IDENTIFIER ::= { ofa731 119 }

		
-- OFA731W gen2 sysOID
		-- 1.3.6.1.4.1.3715.21.731.119.2
		ofa731w-gen2 OBJECT IDENTIFIER ::= { ofa731w 2 }

		
-- OFA731WS gen1 sysOID
		-- 1.3.6.1.4.1.3715.21.731.234
		ofa731ws OBJECT IDENTIFIER ::= { ofa731 234 }

		
-- OFA731WS gen2 sysOID
		-- 1.3.6.1.4.1.3715.21.731.234.2
		ofa731ws-gen2 OBJECT IDENTIFIER ::= { ofa731ws 2 }

		
-- OFA733 gen1 sysOID
		-- 1.3.6.1.4.1.3715.21.733
		ofa733 OBJECT IDENTIFIER ::= { ofa 733 }

		
		-- 1.3.6.1.4.1.3715.21.733.1
		ofa733OutputAttenuation OBJECT-TYPE
			SYNTAX INTEGER
			ACCESS read-write
			STATUS mandatory
			DESCRIPTION
				"Output attenuation.
				
				Unit 0.1 dB."
			::= { ofa733 1 }

		
-- OFA733 gen2 sysOID
		-- 1.3.6.1.4.1.3715.21.733.2
		ofa733-gen2 OBJECT IDENTIFIER ::= { ofa733 2 }

		
-- OFA733S gen1 sysOID
		-- 1.3.6.1.4.1.3715.21.733.115
		ofa733s OBJECT IDENTIFIER ::= { ofa733 115 }

		
-- OFA733S gen2 sysOID
		-- 1.3.6.1.4.1.3715.21.733.115.2
		ofa733s-gen2 OBJECT IDENTIFIER ::= { ofa733s 2 }

		
-- OFA733W gen1 sysOID
		-- 1.3.6.1.4.1.3715.21.733.119
		ofa733w OBJECT IDENTIFIER ::= { ofa733 119 }

		
-- OFA733W gen2 sysOID
		-- 1.3.6.1.4.1.3715.21.733.119.2
		ofa733w-gen2 OBJECT IDENTIFIER ::= { ofa733w 2 }

		
-- OFA733WS gen1 sysOID
		-- 1.3.6.1.4.1.3715.21.733.234
		ofa733ws OBJECT IDENTIFIER ::= { ofa733 234 }

		
-- OFA733WS gen2 sysOID
		-- 1.3.6.1.4.1.3715.21.733.234.2
		ofa733ws-gen2 OBJECT IDENTIFIER ::= { ofa733ws 2 }

		
-- OFA737 gen1 sysOID
		-- 1.3.6.1.4.1.3715.21.737
		ofa737 OBJECT IDENTIFIER ::= { ofa 737 }

		
		-- 1.3.6.1.4.1.3715.21.737.1
		ofa737OutputAttenuation OBJECT-TYPE
			SYNTAX INTEGER
			ACCESS read-write
			STATUS mandatory
			DESCRIPTION
				"Output attenuation.
				
				Unit 0.1 dB."
			::= { ofa737 1 }

		
-- OFA737 gen2 sysOID
		-- 1.3.6.1.4.1.3715.21.737.2
		ofa737gen2 OBJECT IDENTIFIER ::= { ofa737 2 }

		
-- OFA737S gen1 sysOID
		-- 1.3.6.1.4.1.3715.21.737.115
		ofa737s OBJECT IDENTIFIER ::= { ofa737 115 }

		
-- OFA737S gen2 sysOID
		-- 1.3.6.1.4.1.3715.21.737.115.2
		ofa737s-gen2 OBJECT IDENTIFIER ::= { ofa737s 2 }

		
-- OFA737W gen1 sysOID
		-- 1.3.6.1.4.1.3715.21.737.119
		ofa737w OBJECT IDENTIFIER ::= { ofa737 119 }

		
-- OFA737W gen2 sysOID
		-- 1.3.6.1.4.1.3715.21.737.119.2
		ofa737w-gen2 OBJECT IDENTIFIER ::= { ofa737w 2 }

		
-- OFA737WS gen1 sysOID
		-- 1.3.6.1.4.1.3715.21.737.234
		ofa737ws OBJECT IDENTIFIER ::= { ofa737 234 }

		
-- OFA737WS gen2 sysOID
		-- 1.3.6.1.4.1.3715.21.737.234.2
		ofa737ws-gen2 OBJECT IDENTIFIER ::= { ofa737ws 2 }

		
	
	END

--
-- TELESTE-OFA-MIB.mib
--
