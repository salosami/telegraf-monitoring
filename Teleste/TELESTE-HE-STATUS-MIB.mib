--
-- TELESTE-HE-STATUS-MIB.mib
-- MIB generated by MG-SOFT Visual MIB Builder Version 4.0 Build 349
-- Wednesday, January 11, 2012 at 11:00:41
--

-- ****************************************************************************
-- Copyright (c) 2010-2012 by:
--  
-- Teleste Corporation
-- Seponkatu 1
-- FIN-20660 Littoinen, Finland
-- tel. +358 2 2605 611
-- url: http://www.teleste.com
-- 
-- Description: Status objects for IP headend devices
-- ****************************************************************************

	TELESTE-HE-STATUS-MIB DEFINITIONS ::= BEGIN
 
		IMPORTS
			entPhysicalIndex			
				FROM ENTITY-MIB			
			ifIndex			
				FROM RFC1213-MIB			
			OBJECT-GROUP, MODULE-COMPLIANCE			
				FROM SNMPv2-CONF			
			OBJECT-TYPE, MODULE-IDENTITY			
				FROM SNMPv2-SMI			
			functional			
				FROM TELESTE-ROOT-MIB;
	
	
		-- 1.3.6.1.4.1.3715.100.21
		heStatus MODULE-IDENTITY 
			LAST-UPDATED "201201111045Z"		-- January 11, 2012 at 10:45 GMT
			ORGANIZATION 
				"Teleste Corporation"
			CONTACT-INFO 
				"www.teleste.com"
			DESCRIPTION 
				"MIB module for Teleste IP headend status information objects"
			REVISION "201201111045Z"		-- January 11, 2012 at 10:45 GMT
			DESCRIPTION 
				"Second version, corrected root OID"
			REVISION "201102181344Z"		-- February 18, 2011 at 13:44 GMT
			DESCRIPTION 
				"Initial version"
			::= { functional 21 }

		
	
	
--
-- Node definitions
--
	
		-- 1.3.6.1.4.1.3715.100.21.1
		deviceStatusTable OBJECT-TYPE
			SYNTAX SEQUENCE OF DeviceStatusEntry
			MAX-ACCESS not-accessible
			STATUS current
			DESCRIPTION
				"Table of device status objects"
			::= { heStatus 1 }

		
		-- 1.3.6.1.4.1.3715.100.21.1.1
		deviceStatusEntry OBJECT-TYPE
			SYNTAX DeviceStatusEntry
			MAX-ACCESS not-accessible
			STATUS current
			DESCRIPTION
				"Table entry of device status objects"
			INDEX { entPhysicalIndex }
			::= { deviceStatusTable 1 }

		
		DeviceStatusEntry ::=
			SEQUENCE { 
				deviceTemperatureHigh
					INTEGER,
				deviceTemperatureLow
					INTEGER,
				deviceLicenseStatus
					INTEGER,
				deviceAppStatus
					INTEGER,
				deviceModuleStatus
					INTEGER,
				deviceDriverStatus
					INTEGER,
				deviceHwStatus
					INTEGER,
				deviceFanStatus
					INTEGER,
				deviceBackupPowerStatus
					INTEGER,
				deviceRearIOStatus
					INTEGER,
				deviceBackupStatus
					INTEGER,
				deviceEcmgStatus
					INTEGER,
				deviceEcmStreamStatus
					INTEGER,
				deviceEmmStatus
					INTEGER,
				deviceEcmgConfStatus
					INTEGER,
				deviceEmmConnectionStatus
					INTEGER,
				deviceScsStatus
					INTEGER,
				deviceEcmBackupStatus
					INTEGER,
				deviceBootLoaderUpdateStatus
					INTEGER,
				deviceBootLoader1Status
					INTEGER,
				deviceBootLoader2Status
					INTEGER,
				deviceBackupActivityStatus
					INTEGER,
				deviceModuleConfigStatus
					INTEGER
			 }

		-- 1.3.6.1.4.1.3715.100.21.1.1.6
		deviceTemperatureHigh OBJECT-TYPE
			SYNTAX INTEGER
				{
				temperatureOk(1),
				temperatureHigh(2)
				}
			MAX-ACCESS read-only
			STATUS current
			DESCRIPTION
				"Temperature high alarm"
			::= { deviceStatusEntry 6 }

		
		-- 1.3.6.1.4.1.3715.100.21.1.1.7
		deviceTemperatureLow OBJECT-TYPE
			SYNTAX INTEGER
				{
				temperatureOk(1),
				temperatureLow(2)
				}
			MAX-ACCESS read-only
			STATUS current
			DESCRIPTION
				"Temperature low alarm"
			::= { deviceStatusEntry 7 }

		
		-- 1.3.6.1.4.1.3715.100.21.1.1.4107
		deviceLicenseStatus OBJECT-TYPE
			SYNTAX INTEGER
				{
				licenseOk(1),
				licenseConflict(2)
				}
			MAX-ACCESS read-only
			STATUS current
			DESCRIPTION
				"License status"
			::= { deviceStatusEntry 4107 }

		
		-- 1.3.6.1.4.1.3715.100.21.1.1.4108
		deviceAppStatus OBJECT-TYPE
			SYNTAX INTEGER
				{
				appOk(1),
				appError(2),
				appConfiguringModule(3)
				}
			MAX-ACCESS read-only
			STATUS current
			DESCRIPTION
				"Application status"
			::= { deviceStatusEntry 4108 }

		
		-- 1.3.6.1.4.1.3715.100.21.1.1.4111
		deviceModuleStatus OBJECT-TYPE
			SYNTAX INTEGER
				{
				modulesOk(1),
				modulesUnknown(2)
				}
			MAX-ACCESS read-only
			STATUS current
			DESCRIPTION
				"Module status"
			::= { deviceStatusEntry 4111 }

		
		-- 1.3.6.1.4.1.3715.100.21.1.1.4129
		deviceDriverStatus OBJECT-TYPE
			SYNTAX INTEGER
				{
				driverOk(1),
				driverFailure(2)
				}
			MAX-ACCESS read-only
			STATUS current
			DESCRIPTION
				"Device driver status"
			::= { deviceStatusEntry 4129 }

		
		-- 1.3.6.1.4.1.3715.100.21.1.1.4130
		deviceHwStatus OBJECT-TYPE
			SYNTAX INTEGER
				{
				hwOk(1),
				hwFailure(2)
				}
			MAX-ACCESS read-only
			STATUS current
			DESCRIPTION
				"Hardware status"
			::= { deviceStatusEntry 4130 }

		
		-- 1.3.6.1.4.1.3715.100.21.1.1.4131
		deviceFanStatus OBJECT-TYPE
			SYNTAX INTEGER
				{
				fanOk(1),
				fanFail(2)
				}
			MAX-ACCESS read-only
			STATUS current
			DESCRIPTION
				"Fan status"
			::= { deviceStatusEntry 4131 }

		
		-- 1.3.6.1.4.1.3715.100.21.1.1.4132
		deviceBackupPowerStatus OBJECT-TYPE
			SYNTAX INTEGER
				{
				powerOnNormal(1),
				powerOnBackup(2)
				}
			MAX-ACCESS read-only
			STATUS current
			DESCRIPTION
				"Backup power status"
			::= { deviceStatusEntry 4132 }

		
		-- 1.3.6.1.4.1.3715.100.21.1.1.4142
		deviceRearIOStatus OBJECT-TYPE
			SYNTAX INTEGER
				{
				ioModuleOk(1),
				ioModuleFailed(2)
				}
			MAX-ACCESS read-only
			STATUS current
			DESCRIPTION
				"Rear I/O status"
			::= { deviceStatusEntry 4142 }

		
		-- 1.3.6.1.4.1.3715.100.21.1.1.4153
		deviceBackupStatus OBJECT-TYPE
			SYNTAX INTEGER
				{
				backupStatus1(1),
				backupStatus2(2)
				}
			MAX-ACCESS read-only
			STATUS current
			DESCRIPTION
				"Backup status"
			::= { deviceStatusEntry 4153 }

		
		-- 1.3.6.1.4.1.3715.100.21.1.1.4187
		deviceEcmgStatus OBJECT-TYPE
			SYNTAX INTEGER
				{
				ecmgOk(1),
				ecmgFail(2),
				ecmgNotConfigured(3),
				ecmgOnBackup(4)
				}
			MAX-ACCESS read-only
			STATUS current
			DESCRIPTION
				"ECMG status"
			::= { deviceStatusEntry 4187 }

		
		-- 1.3.6.1.4.1.3715.100.21.1.1.4188
		deviceEcmStreamStatus OBJECT-TYPE
			SYNTAX INTEGER
				{
				ecmStreamOk(1),
				ecmStreamFail(2)
				}
			MAX-ACCESS read-only
			STATUS current
			DESCRIPTION
				"ECM stream status"
			::= { deviceStatusEntry 4188 }

		
		-- 1.3.6.1.4.1.3715.100.21.1.1.4189
		deviceEmmStatus OBJECT-TYPE
			SYNTAX INTEGER
				{
				emmOk(1),
				emmFail(2),
				emmNotConnected(3)
				}
			MAX-ACCESS read-only
			STATUS current
			DESCRIPTION
				"EMM status"
			::= { deviceStatusEntry 4189 }

		
		-- 1.3.6.1.4.1.3715.100.21.1.1.4191
		deviceEcmgConfStatus OBJECT-TYPE
			SYNTAX INTEGER
				{
				ecmgOk(1),
				ecmgFail(2),
				ecmgNotConfigured(3),
				ecmgOnBackup(4)
				}
			MAX-ACCESS read-only
			STATUS current
			DESCRIPTION
				"ECMG status"
			::= { deviceStatusEntry 4191 }

		
		-- 1.3.6.1.4.1.3715.100.21.1.1.4192
		deviceEmmConnectionStatus OBJECT-TYPE
			SYNTAX INTEGER
				{
				emmOk(1),
				emmFail(2),
				emmNotConnected(3)
				}
			MAX-ACCESS read-only
			STATUS current
			DESCRIPTION
				"EMM status"
			::= { deviceStatusEntry 4192 }

		
		-- 1.3.6.1.4.1.3715.100.21.1.1.4193
		deviceScsStatus OBJECT-TYPE
			SYNTAX INTEGER
				{
				scsOk(1),
				scsNotLicensed(2)
				}
			MAX-ACCESS read-only
			STATUS current
			DESCRIPTION
				"SCS status"
			::= { deviceStatusEntry 4193 }

		
		-- 1.3.6.1.4.1.3715.100.21.1.1.4194
		deviceEcmBackupStatus OBJECT-TYPE
			SYNTAX INTEGER
				{
				ecmBackupInactive(1),
				ecmBackupActive(2)
				}
			MAX-ACCESS read-only
			STATUS current
			DESCRIPTION
				"ECM backupstatus"
			::= { deviceStatusEntry 4194 }

		
		-- 1.3.6.1.4.1.3715.100.21.1.1.4195
		deviceBootLoaderUpdateStatus OBJECT-TYPE
			SYNTAX INTEGER
				{
				loaderUpToDate(1),
				loaderUpdateAvailable(2)
				}
			MAX-ACCESS read-only
			STATUS current
			DESCRIPTION
				"Boot loader update status"
			::= { deviceStatusEntry 4195 }

		
		-- 1.3.6.1.4.1.3715.100.21.1.1.4198
		deviceBootLoader1Status OBJECT-TYPE
			SYNTAX INTEGER
				{
				loaderOK(1),
				loaderFail(2)
				}
			MAX-ACCESS read-only
			STATUS current
			DESCRIPTION
				"Boot loader 1 status"
			::= { deviceStatusEntry 4198 }

		
		-- 1.3.6.1.4.1.3715.100.21.1.1.4199
		deviceBootLoader2Status OBJECT-TYPE
			SYNTAX INTEGER
				{
				loaderOK(1),
				loaderFail(2)
				}
			MAX-ACCESS read-only
			STATUS current
			DESCRIPTION
				"Boot loader 2 status"
			::= { deviceStatusEntry 4199 }

		
		-- 1.3.6.1.4.1.3715.100.21.1.1.4203
		deviceBackupActivityStatus OBJECT-TYPE
			SYNTAX INTEGER
				{
				backupInactive(1),
				backupActive(2)
				}
			MAX-ACCESS read-only
			STATUS current
			DESCRIPTION
				"Backup activity status"
			::= { deviceStatusEntry 4203 }

		
		-- 1.3.6.1.4.1.3715.100.21.1.1.4205
		deviceModuleConfigStatus OBJECT-TYPE
			SYNTAX INTEGER
				{
				modulesConfigOk(1),
				modulesConfigActive(2)
				}
			MAX-ACCESS read-only
			STATUS current
			DESCRIPTION
				"Module configuration status"
			::= { deviceStatusEntry 4205 }

		
		-- 1.3.6.1.4.1.3715.100.21.2
		moduleStatusTable OBJECT-TYPE
			SYNTAX SEQUENCE OF ModuleStatusEntry
			MAX-ACCESS not-accessible
			STATUS current
			DESCRIPTION
				"Table of module status objects"
			::= { heStatus 2 }

		
		-- 1.3.6.1.4.1.3715.100.21.2.1
		moduleStatusEntry OBJECT-TYPE
			SYNTAX ModuleStatusEntry
			MAX-ACCESS not-accessible
			STATUS current
			DESCRIPTION
				"Table entry of module status objects"
			INDEX { entPhysicalIndex }
			::= { moduleStatusTable 1 }

		
		ModuleStatusEntry ::=
			SEQUENCE { 
				modulePidConflictStatus
					INTEGER,
				moduleStatus
					INTEGER,
				modulePidCapacityStatus
					INTEGER,
				modulePsiSiCapacityStatus
					INTEGER,
				moduleSidStatus
					INTEGER,
				moduleCaModuleStatus
					INTEGER,
				moduleSupplyVoltageHigh
					INTEGER,
				moduleSupplyVoltageLow
					INTEGER,
				moduleSupplyCurrentHigh
					INTEGER,
				moduleSupplyCurrentLow
					INTEGER,
				modulePsuPowerStatus
					INTEGER,
				moduleBootUpStatus
					INTEGER,
				moduleBoot1Status
					INTEGER,
				moduleBootFailed
					INTEGER,
				moduleShutDownStatus
					INTEGER,
				moduleConnectionStatus
					INTEGER,
				moduleDisableStatus
					INTEGER,
				moduleBoot2Status
					INTEGER,
				moduleBootStatus
					INTEGER,
				moduleUpconverterCommStatus
					INTEGER,
				moduleUpconverterPllStatus
					INTEGER,
				moduleUpconverterLevelLow
					INTEGER,
				moduleUpconverterLevelHigh
					INTEGER,
				moduleUpconverterCalDataStatus
					INTEGER,
				moduleDescramblerStatus
					INTEGER,
				moduleBootingStatus
					INTEGER,
				moduleRestartStatus
					INTEGER,
				moduleFPGAStatus
					INTEGER,
				moduleCpuStatus
					INTEGER,
				moduleSidConflictStatus
					INTEGER,
				modulePIDAllocationtStatus
					INTEGER,
				moduleDvbConfigUnsupported
					INTEGER,
				moduleDvbFreqStatus
					INTEGER,
				moduleDvbOutputPowerStatus
					INTEGER,
				moduleDvbSymbolRateStatus
					INTEGER,
				moduleDvbChannelDistanceStatus
					INTEGER,
				moduleDvbConfigInvalid
					INTEGER,
				moduleDvbPuncRateStatus
					INTEGER,
				moduleLNBCurrentStatus
					INTEGER,
				moduleDVBFreqOffsetStatus
					INTEGER,
				moduleCamStatus
					INTEGER,
				moduleCamRebootStatus
					INTEGER
			 }

		-- 1.3.6.1.4.1.3715.100.21.2.1.4
		modulePidConflictStatus OBJECT-TYPE
			SYNTAX INTEGER
				{
				noPidConflict(1),
				pidConflict(2)
				}
			MAX-ACCESS read-only
			STATUS current
			DESCRIPTION
				"PID conflict status"
			::= { moduleStatusEntry 4 }

		
		-- 1.3.6.1.4.1.3715.100.21.2.1.4096
		moduleStatus OBJECT-TYPE
			SYNTAX INTEGER
				{
				moduleOk(1),
				moduleOff(2)
				}
			MAX-ACCESS read-only
			STATUS current
			DESCRIPTION
				"Module general status"
			::= { moduleStatusEntry 4096 }

		
		-- 1.3.6.1.4.1.3715.100.21.2.1.4104
		modulePidCapacityStatus OBJECT-TYPE
			SYNTAX INTEGER
				{
				capacityOk(1),
				capacityExceeded(2)
				}
			MAX-ACCESS read-only
			STATUS current
			DESCRIPTION
				"PID capacity status"
			::= { moduleStatusEntry 4104 }

		
		-- 1.3.6.1.4.1.3715.100.21.2.1.4105
		modulePsiSiCapacityStatus OBJECT-TYPE
			SYNTAX INTEGER
				{
				capacityOk(1),
				capacityExceeded(2)
				}
			MAX-ACCESS read-only
			STATUS current
			DESCRIPTION
				"PSI/SI capacity status"
			::= { moduleStatusEntry 4105 }

		
		-- 1.3.6.1.4.1.3715.100.21.2.1.4106
		moduleSidStatus OBJECT-TYPE
			SYNTAX INTEGER
				{
				sidOk(1),
				sidOutOfRange(2)
				}
			MAX-ACCESS read-only
			STATUS current
			DESCRIPTION
				"SID status"
			::= { moduleStatusEntry 4106 }

		
		-- 1.3.6.1.4.1.3715.100.21.2.1.4108
		moduleCaModuleStatus OBJECT-TYPE
			SYNTAX INTEGER
				{
				caModuleOk(1),
				caModuleMissing(2)
				}
			MAX-ACCESS read-only
			STATUS current
			DESCRIPTION
				"CA module status"
			::= { moduleStatusEntry 4108 }

		
		-- 1.3.6.1.4.1.3715.100.21.2.1.4112
		moduleSupplyVoltageHigh OBJECT-TYPE
			SYNTAX INTEGER
				{
				voltageOk(1),
				voltageHigh(2)
				}
			MAX-ACCESS read-only
			STATUS current
			DESCRIPTION
				"Supply voltage high alarm"
			::= { moduleStatusEntry 4112 }

		
		-- 1.3.6.1.4.1.3715.100.21.2.1.4113
		moduleSupplyVoltageLow OBJECT-TYPE
			SYNTAX INTEGER
				{
				voltageOk(1),
				voltageLow(2)
				}
			MAX-ACCESS read-only
			STATUS current
			DESCRIPTION
				"Supply voltage low alarm"
			::= { moduleStatusEntry 4113 }

		
		-- 1.3.6.1.4.1.3715.100.21.2.1.4114
		moduleSupplyCurrentHigh OBJECT-TYPE
			SYNTAX INTEGER
				{
				currentOk(1),
				currentHigh(2)
				}
			MAX-ACCESS read-only
			STATUS current
			DESCRIPTION
				"Supply current high alarm"
			::= { moduleStatusEntry 4114 }

		
		-- 1.3.6.1.4.1.3715.100.21.2.1.4115
		moduleSupplyCurrentLow OBJECT-TYPE
			SYNTAX INTEGER
				{
				currentOk(1),
				currentLow(2)
				}
			MAX-ACCESS read-only
			STATUS current
			DESCRIPTION
				"Supply current low alarm"
			::= { moduleStatusEntry 4115 }

		
		-- 1.3.6.1.4.1.3715.100.21.2.1.4133
		modulePsuPowerStatus OBJECT-TYPE
			SYNTAX INTEGER
				{
				psuOk(1),
				psuOverload(2)
				}
			MAX-ACCESS read-only
			STATUS current
			DESCRIPTION
				"Power supply output power status"
			::= { moduleStatusEntry 4133 }

		
		-- 1.3.6.1.4.1.3715.100.21.2.1.4134
		moduleBootUpStatus OBJECT-TYPE
			SYNTAX INTEGER
				{
				bootingOk(1),
				bootingUp(2)
				}
			MAX-ACCESS read-only
			STATUS current
			DESCRIPTION
				"Module boot up status"
			::= { moduleStatusEntry 4134 }

		
		-- 1.3.6.1.4.1.3715.100.21.2.1.4135
		moduleBoot1Status OBJECT-TYPE
			SYNTAX INTEGER
				{
				bootOk(1),
				bootFailed(2)
				}
			MAX-ACCESS read-only
			STATUS current
			DESCRIPTION
				"Module boot failed status"
			::= { moduleStatusEntry 4135 }

		
		-- 1.3.6.1.4.1.3715.100.21.2.1.4136
		moduleBootFailed OBJECT-TYPE
			SYNTAX INTEGER
				{
				bootingOk(1),
				bootFailed(2)
				}
			MAX-ACCESS read-only
			STATUS current
			DESCRIPTION
				"Module boot failed alarm"
			::= { moduleStatusEntry 4136 }

		
		-- 1.3.6.1.4.1.3715.100.21.2.1.4137
		moduleShutDownStatus OBJECT-TYPE
			SYNTAX INTEGER
				{
				shutdownOk(1),
				shuttingDown(2)
				}
			MAX-ACCESS read-only
			STATUS current
			DESCRIPTION
				"Module shutdown status"
			::= { moduleStatusEntry 4137 }

		
		-- 1.3.6.1.4.1.3715.100.21.2.1.4138
		moduleConnectionStatus OBJECT-TYPE
			SYNTAX INTEGER
				{
				connectionOk(1),
				connectionLost(2)
				}
			MAX-ACCESS read-only
			STATUS current
			DESCRIPTION
				"Module connection status"
			::= { moduleStatusEntry 4138 }

		
		-- 1.3.6.1.4.1.3715.100.21.2.1.4139
		moduleDisableStatus OBJECT-TYPE
			SYNTAX INTEGER
				{
				modulaEnabled(1),
				moduleDisabled(2)
				}
			MAX-ACCESS read-only
			STATUS current
			DESCRIPTION
				"Module enabled/disabled status"
			::= { moduleStatusEntry 4139 }

		
		-- 1.3.6.1.4.1.3715.100.21.2.1.4140
		moduleBoot2Status OBJECT-TYPE
			SYNTAX INTEGER
				{
				bootOk(1),
				bootFailed(2)
				}
			MAX-ACCESS read-only
			STATUS current
			DESCRIPTION
				"Module boot 2 status"
			::= { moduleStatusEntry 4140 }

		
		-- 1.3.6.1.4.1.3715.100.21.2.1.4141
		moduleBootStatus OBJECT-TYPE
			SYNTAX INTEGER
				{
				bootOk(1),
				bootFailed(2)
				}
			MAX-ACCESS read-only
			STATUS current
			DESCRIPTION
				"Module boot status"
			::= { moduleStatusEntry 4141 }

		
		-- 1.3.6.1.4.1.3715.100.21.2.1.4145
		moduleUpconverterCommStatus OBJECT-TYPE
			SYNTAX INTEGER
				{
				upconverterOk(1),
				upconverterTimeout(2)
				}
			MAX-ACCESS read-only
			STATUS current
			DESCRIPTION
				"Upconverter communication status"
			::= { moduleStatusEntry 4145 }

		
		-- 1.3.6.1.4.1.3715.100.21.2.1.4146
		moduleUpconverterPllStatus OBJECT-TYPE
			SYNTAX INTEGER
				{
				pllOk(1),
				pllFailure(2)
				}
			MAX-ACCESS read-only
			STATUS current
			DESCRIPTION
				"Upconverter PLL status"
			::= { moduleStatusEntry 4146 }

		
		-- 1.3.6.1.4.1.3715.100.21.2.1.4147
		moduleUpconverterLevelLow OBJECT-TYPE
			SYNTAX INTEGER
				{
				inputOk(1),
				inputLow(2)
				}
			MAX-ACCESS read-only
			STATUS current
			DESCRIPTION
				"Upconverter level low alarm"
			::= { moduleStatusEntry 4147 }

		
		-- 1.3.6.1.4.1.3715.100.21.2.1.4148
		moduleUpconverterLevelHigh OBJECT-TYPE
			SYNTAX INTEGER
				{
				inputOk(1),
				inputHigh(2)
				}
			MAX-ACCESS read-only
			STATUS current
			DESCRIPTION
				"Upconverter level hihg alarm"
			::= { moduleStatusEntry 4148 }

		
		-- 1.3.6.1.4.1.3715.100.21.2.1.4149
		moduleUpconverterCalDataStatus OBJECT-TYPE
			SYNTAX INTEGER
				{
				calDataOk(1),
				calDataFailure(2)
				}
			MAX-ACCESS read-only
			STATUS current
			DESCRIPTION
				"Upconverter calibration data status"
			::= { moduleStatusEntry 4149 }

		
		-- 1.3.6.1.4.1.3715.100.21.2.1.4151
		moduleDescramblerStatus OBJECT-TYPE
			SYNTAX INTEGER
				{
				descramblerOk(1),
				descramblerFailure(2)
				}
			MAX-ACCESS read-only
			STATUS current
			DESCRIPTION
				"Module descrambler status"
			::= { moduleStatusEntry 4151 }

		
		-- 1.3.6.1.4.1.3715.100.21.2.1.4167
		moduleBootingStatus OBJECT-TYPE
			SYNTAX INTEGER
				{
				bootingOk(1),
				bootingUp(2)
				}
			MAX-ACCESS read-only
			STATUS current
			DESCRIPTION
				"Module booting status"
			::= { moduleStatusEntry 4167 }

		
		-- 1.3.6.1.4.1.3715.100.21.2.1.4168
		moduleRestartStatus OBJECT-TYPE
			SYNTAX INTEGER
				{
				restartOk(1),
				restarting(2)
				}
			MAX-ACCESS read-only
			STATUS current
			DESCRIPTION
				"Module restart status"
			::= { moduleStatusEntry 4168 }

		
		-- 1.3.6.1.4.1.3715.100.21.2.1.4171
		moduleFPGAStatus OBJECT-TYPE
			SYNTAX INTEGER
				{
				fpgaOk(1),
				fpgaFailure(2)
				}
			MAX-ACCESS read-only
			STATUS current
			DESCRIPTION
				"Module FPGA status"
			::= { moduleStatusEntry 4171 }

		
		-- 1.3.6.1.4.1.3715.100.21.2.1.4172
		moduleCpuStatus OBJECT-TYPE
			SYNTAX INTEGER
				{
				cpuOk(1),
				cpuFailure(2)
				}
			MAX-ACCESS read-only
			STATUS current
			DESCRIPTION
				"Module CPU status"
			::= { moduleStatusEntry 4172 }

		
		-- 1.3.6.1.4.1.3715.100.21.2.1.4173
		moduleSidConflictStatus OBJECT-TYPE
			SYNTAX INTEGER
				{
				sidNoConflict(1),
				sidConflict(2)
				}
			MAX-ACCESS read-only
			STATUS current
			DESCRIPTION
				"Module SID conflict status"
			::= { moduleStatusEntry 4173 }

		
		-- 1.3.6.1.4.1.3715.100.21.2.1.4174
		modulePIDAllocationtStatus OBJECT-TYPE
			SYNTAX INTEGER
				{
				pidAllocOk(1),
				pidAllocFail(2)
				}
			MAX-ACCESS read-only
			STATUS current
			DESCRIPTION
				"Module PID allocation status"
			::= { moduleStatusEntry 4174 }

		
		-- 1.3.6.1.4.1.3715.100.21.2.1.4175
		moduleDvbConfigUnsupported OBJECT-TYPE
			SYNTAX INTEGER
				{
				configOk(1),
				configUnsupported(2)
				}
			MAX-ACCESS read-only
			STATUS current
			DESCRIPTION
				"DVB configuration support status"
			::= { moduleStatusEntry 4175 }

		
		-- 1.3.6.1.4.1.3715.100.21.2.1.4176
		moduleDvbFreqStatus OBJECT-TYPE
			SYNTAX INTEGER
				{
				frequencyOk(1),
				frequencyOutOfRange(2)
				}
			MAX-ACCESS read-only
			STATUS current
			DESCRIPTION
				"DVB frequency status"
			::= { moduleStatusEntry 4176 }

		
		-- 1.3.6.1.4.1.3715.100.21.2.1.4177
		moduleDvbOutputPowerStatus OBJECT-TYPE
			SYNTAX INTEGER
				{
				levelOk(1),
				powerOutOfRange(2)
				}
			MAX-ACCESS read-only
			STATUS current
			DESCRIPTION
				"DVB output power/level status"
			::= { moduleStatusEntry 4177 }

		
		-- 1.3.6.1.4.1.3715.100.21.2.1.4178
		moduleDvbSymbolRateStatus OBJECT-TYPE
			SYNTAX INTEGER
				{
				symbolRateOk(1),
				symbolrateOutOfRange(2)
				}
			MAX-ACCESS read-only
			STATUS current
			DESCRIPTION
				"DVB symbol rate status"
			::= { moduleStatusEntry 4178 }

		
		-- 1.3.6.1.4.1.3715.100.21.2.1.4179
		moduleDvbChannelDistanceStatus OBJECT-TYPE
			SYNTAX INTEGER
				{
				channelOk(1),
				channelTooClose(2)
				}
			MAX-ACCESS read-only
			STATUS current
			DESCRIPTION
				"DVB channel distance status"
			::= { moduleStatusEntry 4179 }

		
		-- 1.3.6.1.4.1.3715.100.21.2.1.4180
		moduleDvbConfigInvalid OBJECT-TYPE
			SYNTAX INTEGER
				{
				configOk(1),
				configInvalid(2)
				}
			MAX-ACCESS read-only
			STATUS current
			DESCRIPTION
				"DVB configuration status"
			::= { moduleStatusEntry 4180 }

		
		-- 1.3.6.1.4.1.3715.100.21.2.1.4181
		moduleDvbPuncRateStatus OBJECT-TYPE
			SYNTAX INTEGER
				{
				rateOk(1),
				rateInvalid(2)
				}
			MAX-ACCESS read-only
			STATUS current
			DESCRIPTION
				"DVB puncture rate status, DVB-T only"
			::= { moduleStatusEntry 4181 }

		
		-- 1.3.6.1.4.1.3715.100.21.2.1.4182
		moduleLNBCurrentStatus OBJECT-TYPE
			SYNTAX INTEGER
				{
				currentOk(1),
				currentOutOfRange(2)
				}
			MAX-ACCESS read-only
			STATUS current
			DESCRIPTION
				"LNB current status"
			::= { moduleStatusEntry 4182 }

		
		-- 1.3.6.1.4.1.3715.100.21.2.1.4183
		moduleDVBFreqOffsetStatus OBJECT-TYPE
			SYNTAX INTEGER
				{
				offsetOk(1),
				offsetOutOfRange(2)
				}
			MAX-ACCESS read-only
			STATUS current
			DESCRIPTION
				"DVB frequency offset status"
			::= { moduleStatusEntry 4183 }

		
		-- 1.3.6.1.4.1.3715.100.21.2.1.4185
		moduleCamStatus OBJECT-TYPE
			SYNTAX INTEGER
				{
				camOk(1),
				camRestarting(2)
				}
			MAX-ACCESS read-only
			STATUS current
			DESCRIPTION
				"Module CAM status"
			::= { moduleStatusEntry 4185 }

		
		-- 1.3.6.1.4.1.3715.100.21.2.1.4186
		moduleCamRebootStatus OBJECT-TYPE
			SYNTAX INTEGER
				{
				camOk(1),
				camBooting(2)
				}
			MAX-ACCESS read-only
			STATUS current
			DESCRIPTION
				"Module CAM reboot status"
			::= { moduleStatusEntry 4186 }

		
		-- 1.3.6.1.4.1.3715.100.21.3
		ifStatusTable OBJECT-TYPE
			SYNTAX SEQUENCE OF IfStatusEntry
			MAX-ACCESS not-accessible
			STATUS current
			DESCRIPTION
				"Table of interface status objects"
			::= { heStatus 3 }

		
		-- 1.3.6.1.4.1.3715.100.21.3.1
		ifStatusEntry OBJECT-TYPE
			SYNTAX IfStatusEntry
			MAX-ACCESS not-accessible
			STATUS current
			DESCRIPTION
				"Table entry of interface status objects"
			INDEX { entPhysicalIndex, ifIndex }
			::= { ifStatusTable 1 }

		
		IfStatusEntry ::=
			SEQUENCE { 
				signalStatus
					INTEGER,
				asiLinkStatus
					INTEGER,
				signalQualityStatus
					INTEGER
			 }

		-- 1.3.6.1.4.1.3715.100.21.3.1.4097
		signalStatus OBJECT-TYPE
			SYNTAX INTEGER
				{
				signalOk(1),
				signalMissing(2)
				}
			MAX-ACCESS read-only
			STATUS current
			DESCRIPTION
				"Interface signal status"
			::= { ifStatusEntry 4097 }

		
		-- 1.3.6.1.4.1.3715.100.21.3.1.4102
		asiLinkStatus OBJECT-TYPE
			SYNTAX INTEGER
				{
				linkOk(1),
				linkDown(2)
				}
			MAX-ACCESS read-only
			STATUS current
			DESCRIPTION
				"ASI link status"
			::= { ifStatusEntry 4102 }

		
		-- 1.3.6.1.4.1.3715.100.21.3.1.4161
		signalQualityStatus OBJECT-TYPE
			SYNTAX INTEGER
				{
				signalOk(1),
				signalQualityLow(2)
				}
			MAX-ACCESS read-only
			STATUS current
			DESCRIPTION
				"Interface signal quality status"
			::= { ifStatusEntry 4161 }

		
		-- 1.3.6.1.4.1.3715.100.21.4
		tsStatusTable OBJECT-TYPE
			SYNTAX SEQUENCE OF TsStatusEntry
			MAX-ACCESS not-accessible
			STATUS current
			DESCRIPTION
				"Table of transport stream status objects"
			::= { heStatus 4 }

		
		-- 1.3.6.1.4.1.3715.100.21.4.1
		tsStatusEntry OBJECT-TYPE
			SYNTAX TsStatusEntry
			MAX-ACCESS not-accessible
			STATUS current
			DESCRIPTION
				"Table entry of transport stream status objects"
			INDEX { entPhysicalIndex, ifIndex, tsId }
			::= { tsStatusTable 1 }

		
		TsStatusEntry ::=
			SEQUENCE { 
				tsId
					INTEGER,
				tsPidRemappingStatus
					INTEGER,
				tsManualInsertionStatus
					INTEGER,
				tsSyncStatus
					INTEGER,
				tsReceiverStatus
					INTEGER,
				tsInputBufferStatus
					INTEGER,
				tsOutputBufferStatus
					INTEGER,
				tsPsiSiInsertionStatus
					INTEGER,
				tsMultiplexStatus
					INTEGER
			 }

		-- 1.3.6.1.4.1.3715.100.21.4.1.1
		tsId OBJECT-TYPE
			SYNTAX INTEGER (1..65535)
			MAX-ACCESS read-only
			STATUS current
			DESCRIPTION
				"TS = Transport stream identifier"
			::= { tsStatusEntry 1 }

		
		-- 1.3.6.1.4.1.3715.100.21.4.1.5
		tsPidRemappingStatus OBJECT-TYPE
			SYNTAX INTEGER
				{
				notRemapped(1),
				remapped(2)
				}
			MAX-ACCESS read-only
			STATUS current
			DESCRIPTION
				"TS PID remapping status"
			::= { tsStatusEntry 5 }

		
		-- 1.3.6.1.4.1.3715.100.21.4.1.8
		tsManualInsertionStatus OBJECT-TYPE
			SYNTAX INTEGER
				{
				insertionOk(1),
				insertionFailed(2)
				}
			MAX-ACCESS read-only
			STATUS current
			DESCRIPTION
				"TS manual insertion status"
			::= { tsStatusEntry 8 }

		
		-- 1.3.6.1.4.1.3715.100.21.4.1.4098
		tsSyncStatus OBJECT-TYPE
			SYNTAX INTEGER
				{
				syncOk(1),
				syncNoSync(2)
				}
			MAX-ACCESS read-only
			STATUS current
			DESCRIPTION
				"TS synchronisation status"
			::= { tsStatusEntry 4098 }

		
		-- 1.3.6.1.4.1.3715.100.21.4.1.4099
		tsReceiverStatus OBJECT-TYPE
			SYNTAX INTEGER
				{
				receiverOk(1),
				receiverError(2)
				}
			MAX-ACCESS read-only
			STATUS current
			DESCRIPTION
				"TS receiver status"
			::= { tsStatusEntry 4099 }

		
		-- 1.3.6.1.4.1.3715.100.21.4.1.4100
		tsInputBufferStatus OBJECT-TYPE
			SYNTAX INTEGER
				{
				bufferOk(1),
				bufferOverflow(2)
				}
			MAX-ACCESS read-only
			STATUS current
			DESCRIPTION
				"TS input buffer status"
			::= { tsStatusEntry 4100 }

		
		-- 1.3.6.1.4.1.3715.100.21.4.1.4101
		tsOutputBufferStatus OBJECT-TYPE
			SYNTAX INTEGER
				{
				bufferOk(1),
				bufferOverflow(2)
				}
			MAX-ACCESS read-only
			STATUS current
			DESCRIPTION
				"TS output buffer status"
			::= { tsStatusEntry 4101 }

		
		-- 1.3.6.1.4.1.3715.100.21.4.1.4109
		tsPsiSiInsertionStatus OBJECT-TYPE
			SYNTAX INTEGER
				{
				ok(1),
				capacityExceeded(2)
				}
			MAX-ACCESS read-only
			STATUS current
			DESCRIPTION
				"TS PSI/SI insertion status"
			::= { tsStatusEntry 4109 }

		
		-- 1.3.6.1.4.1.3715.100.21.4.1.4110
		tsMultiplexStatus OBJECT-TYPE
			SYNTAX INTEGER
				{
				multiplexOk(1),
				multiplexOverallocated(2)
				}
			MAX-ACCESS read-only
			STATUS current
			DESCRIPTION
				"TS multiplex status"
			::= { tsStatusEntry 4110 }

		
		-- 1.3.6.1.4.1.3715.100.21.5
		serviceStatusTable OBJECT-TYPE
			SYNTAX SEQUENCE OF ServiceStatusEntry
			MAX-ACCESS not-accessible
			STATUS current
			DESCRIPTION
				"Table of service status objects"
			::= { heStatus 5 }

		
		-- 1.3.6.1.4.1.3715.100.21.5.1
		serviceStatusEntry OBJECT-TYPE
			SYNTAX ServiceStatusEntry
			MAX-ACCESS not-accessible
			STATUS current
			DESCRIPTION
				"Table entry of service status objects"
			INDEX { entPhysicalIndex, ifIndex, tsId, serviceId }
			::= { serviceStatusTable 1 }

		
		ServiceStatusEntry ::=
			SEQUENCE { 
				serviceId
					INTEGER,
				serviceStatus
					INTEGER
			 }

		-- 1.3.6.1.4.1.3715.100.21.5.1.1
		serviceId OBJECT-TYPE
			SYNTAX INTEGER (1..65535)
			MAX-ACCESS read-only
			STATUS current
			DESCRIPTION
				"SID = Service ID"
			::= { serviceStatusEntry 1 }

		
		-- 1.3.6.1.4.1.3715.100.21.5.1.3
		serviceStatus OBJECT-TYPE
			SYNTAX INTEGER
				{
				servicePresent(1),
				serviceMissing(2)
				}
			MAX-ACCESS read-only
			STATUS current
			DESCRIPTION
				"Service status"
			::= { serviceStatusEntry 3 }

		
		-- 1.3.6.1.4.1.3715.100.21.6
		pidStatusTable OBJECT-TYPE
			SYNTAX SEQUENCE OF PidStatusEntry
			MAX-ACCESS not-accessible
			STATUS current
			DESCRIPTION
				"Table of PID status objects"
			::= { heStatus 6 }

		
		-- 1.3.6.1.4.1.3715.100.21.6.1
		pidStatusEntry OBJECT-TYPE
			SYNTAX PidStatusEntry
			MAX-ACCESS not-accessible
			STATUS current
			DESCRIPTION
				"Table entry of PID status objects"
			INDEX { entPhysicalIndex, ifIndex, tsId, serviceId, pId
				 }
			::= { pidStatusTable 1 }

		
		PidStatusEntry ::=
			SEQUENCE { 
				pId
					INTEGER,
				pidStatus
					INTEGER
			 }

		-- 1.3.6.1.4.1.3715.100.21.6.1.1
		pId OBJECT-TYPE
			SYNTAX INTEGER (1..65535)
			MAX-ACCESS read-only
			STATUS current
			DESCRIPTION
				"PID = Program Identifier"
			::= { pidStatusEntry 1 }

		
		-- 1.3.6.1.4.1.3715.100.21.6.1.2
		pidStatus OBJECT-TYPE
			SYNTAX INTEGER
				{
				pidPresent(1),
				pidMissing(2)
				}
			MAX-ACCESS read-only
			STATUS current
			DESCRIPTION
				"PID status"
			::= { pidStatusEntry 2 }

		
		-- 1.3.6.1.4.1.3715.100.21.7
		heStatusConformance OBJECT IDENTIFIER ::= { heStatus 7 }

		
		-- 1.3.6.1.4.1.3715.100.21.7.1
		heStatusGroups OBJECT IDENTIFIER ::= { heStatusConformance 1 }

		
		-- 1.3.6.1.4.1.3715.100.21.7.1.1
		heStatusDeviceGroup OBJECT-GROUP
			OBJECTS { deviceTemperatureHigh, deviceTemperatureLow, deviceLicenseStatus, deviceAppStatus, deviceModuleStatus, 
				deviceHwStatus, deviceFanStatus, deviceBackupPowerStatus, deviceBackupStatus, deviceDriverStatus, 
				deviceRearIOStatus, deviceEcmgStatus, deviceEcmStreamStatus, deviceEmmStatus, deviceEcmgConfStatus, 
				deviceEmmConnectionStatus, deviceScsStatus, deviceEcmBackupStatus, deviceBootLoaderUpdateStatus, deviceBootLoader1Status, 
				deviceBootLoader2Status, deviceBackupActivityStatus, deviceModuleConfigStatus }
			STATUS current
			DESCRIPTION 
				"Description."
			::= { heStatusGroups 1 }

		
		-- 1.3.6.1.4.1.3715.100.21.7.1.2
		heStatusModuleGroup OBJECT-GROUP
			OBJECTS { modulePidConflictStatus, moduleStatus, modulePidCapacityStatus, modulePsiSiCapacityStatus, moduleSidStatus, 
				moduleCaModuleStatus, moduleSupplyVoltageHigh, moduleSupplyVoltageLow, moduleSupplyCurrentHigh, moduleSupplyCurrentLow, 
				modulePsuPowerStatus, moduleBootUpStatus, moduleBoot1Status, moduleBootFailed, moduleShutDownStatus, 
				moduleConnectionStatus, moduleDisableStatus, moduleBoot2Status, moduleBootStatus, moduleUpconverterCommStatus, 
				moduleUpconverterPllStatus, moduleUpconverterLevelLow, moduleUpconverterLevelHigh, moduleUpconverterCalDataStatus, moduleDescramblerStatus, 
				moduleBootingStatus, moduleRestartStatus, moduleFPGAStatus, moduleCpuStatus, moduleSidConflictStatus, 
				modulePIDAllocationtStatus, moduleDvbConfigUnsupported, moduleDvbFreqStatus, moduleDvbOutputPowerStatus, moduleDvbSymbolRateStatus, 
				moduleDvbChannelDistanceStatus, moduleDvbConfigInvalid, moduleDvbPuncRateStatus, moduleLNBCurrentStatus, moduleDVBFreqOffsetStatus, 
				moduleCamStatus, moduleCamRebootStatus }
			STATUS current
			DESCRIPTION 
				"Description."
			::= { heStatusGroups 2 }

		
		-- 1.3.6.1.4.1.3715.100.21.7.1.3
		heStatusIfGroup OBJECT-GROUP
			OBJECTS { signalStatus, asiLinkStatus, signalQualityStatus }
			STATUS current
			DESCRIPTION 
				"Description."
			::= { heStatusGroups 3 }

		
		-- 1.3.6.1.4.1.3715.100.21.7.1.4
		heStatusTsGroup OBJECT-GROUP
			OBJECTS { tsPidRemappingStatus, tsManualInsertionStatus, tsSyncStatus, tsReceiverStatus, tsInputBufferStatus, 
				tsOutputBufferStatus, tsPsiSiInsertionStatus, tsMultiplexStatus, tsId }
			STATUS current
			DESCRIPTION 
				"Description."
			::= { heStatusGroups 4 }

		
		-- 1.3.6.1.4.1.3715.100.21.7.1.5
		heStatusServiceGroup OBJECT-GROUP
			OBJECTS { serviceStatus, serviceId }
			STATUS current
			DESCRIPTION 
				"Description."
			::= { heStatusGroups 5 }

		
		-- 1.3.6.1.4.1.3715.100.21.7.1.6
		heStatusPidGroup OBJECT-GROUP
			OBJECTS { pidStatus, pId }
			STATUS current
			DESCRIPTION 
				"Description."
			::= { heStatusGroups 6 }

		
		-- 1.3.6.1.4.1.3715.100.21.7.2
		heStatusCompliances OBJECT IDENTIFIER ::= { heStatusConformance 2 }

		
		-- 1.3.6.1.4.1.3715.100.21.7.2.1
		heStatusBasicCompliance MODULE-COMPLIANCE
			STATUS current
			DESCRIPTION 
				"Description."
			::= { heStatusCompliances 1 }

		
	
	END

--
-- TELESTE-HE-STATUS-MIB.mib
--
