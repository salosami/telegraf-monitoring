--
-- TELESTE-HEADEND-MIB.mib
-- MIB generated by MG-SOFT Visual MIB Builder Version 4.0 Build 349
-- Thursday, December 21, 2006 at 14:49:57
--

-- *****************************************************************************
-- Copyright (c) 2000-2006 by:
-- 
-- Teleste Corporation
-- Seponkatu 1
-- FIN-20660 Littoinen, Finland
-- tel. +358 2 2605 611
-- url: http://www.teleste.com
-- 
-- Description: Headend functions MIB
-- 
-- Revision History:
-- -----------------
-- 1.0  21.12.2006 Matti Susi
-- - First official release
-- 
-- ****************************************************************************

	TELESTE-HEADEND-MIB DEFINITIONS ::= BEGIN
 
		IMPORTS
			OBJECT-TYPE			
				FROM RFC-1212			
			headEnd			
				FROM TELESTE-ROOT-MIB;
	
	
--
-- Node definitions
--
	
		-- 1.3.6.1.4.1.3715.100.20.1
		powerSupply OBJECT IDENTIFIER ::= { headEnd 1 }

		
		-- 1.3.6.1.4.1.3715.100.20.1.1
		voltage6v3Status OBJECT-TYPE
			SYNTAX INTEGER
				{
				normal(1),
				outLimits(2)
				}
			ACCESS read-only
			STATUS mandatory
			DESCRIPTION
				"6.3 V output voltage status."
			::= { powerSupply 1 }

		
		-- 1.3.6.1.4.1.3715.100.20.1.2
		voltage12v5Status OBJECT-TYPE
			SYNTAX INTEGER
				{
				normal(1),
				outLimits(2)
				}
			ACCESS read-only
			STATUS mandatory
			DESCRIPTION
				"12.5 V output voltage status."
			::= { powerSupply 2 }

		
		-- 1.3.6.1.4.1.3715.100.20.1.3
		voltage25vStatus OBJECT-TYPE
			SYNTAX INTEGER
				{
				normal(1),
				outLimits(2)
				}
			ACCESS read-only
			STATUS mandatory
			DESCRIPTION
				"25 V output voltage status."
			::= { powerSupply 3 }

		
		-- 1.3.6.1.4.1.3715.100.20.1.4
		current6v3Status OBJECT-TYPE
			SYNTAX INTEGER
				{
				normal(1),
				overload(2)
				}
			ACCESS read-only
			STATUS mandatory
			DESCRIPTION
				"6.3 V output current status."
			::= { powerSupply 4 }

		
		-- 1.3.6.1.4.1.3715.100.20.1.5
		current12v5Status OBJECT-TYPE
			SYNTAX INTEGER
				{
				normal(1),
				overload(2)
				}
			ACCESS read-only
			STATUS mandatory
			DESCRIPTION
				"12.5 V output current status."
			::= { powerSupply 5 }

		
		-- 1.3.6.1.4.1.3715.100.20.1.6
		current25vStatus OBJECT-TYPE
			SYNTAX INTEGER
				{
				normal(1),
				overload(2)
				}
			ACCESS read-only
			STATUS mandatory
			DESCRIPTION
				"25 V output current status."
			::= { powerSupply 6 }

		
		-- 1.3.6.1.4.1.3715.100.20.1.7
		mainsPowerStatus OBJECT-TYPE
			SYNTAX INTEGER
				{
				mainsNormal(1),
				mainsOverload(2),
				powerMissing(3)
				}
			ACCESS read-only
			STATUS mandatory
			DESCRIPTION
				"Mains power status:
				1 = Mains input is normal
				2 = Mains input is overloaded (all outputs overloaded)
				3 = Mains input is missing"
			::= { powerSupply 7 }
-- Mains power status.
		
		-- 1.3.6.1.4.1.3715.100.20.1.8
		totalOutputPower OBJECT-TYPE
			SYNTAX INTEGER
			ACCESS read-only
			STATUS optional
			DESCRIPTION
				"Total output power of the power supply. Unit 0.1 watt."
			::= { powerSupply 8 }

		
		-- 1.3.6.1.4.1.3715.100.20.2
		downConverter OBJECT IDENTIFIER ::= { headEnd 2 }

		
		-- 1.3.6.1.4.1.3715.100.20.2.1
		inputFrequency OBJECT-TYPE
			SYNTAX INTEGER
			ACCESS read-write
			STATUS mandatory
			DESCRIPTION
				"Input frequency. Unit 1 kHz.
				For analogue television signals, the vision carrier frequency.
				For QAM signals, the centre (carrier) frequency)."
			::= { downConverter 1 }

		
		-- 1.3.6.1.4.1.3715.100.20.2.2
		inputLevel OBJECT-TYPE
			SYNTAX INTEGER
			ACCESS read-only
			STATUS mandatory
			DESCRIPTION
				"Input level. Unit 0.1 dBuV.
				Use of other units is possible depending on the module type."
			::= { downConverter 2 }

		
		-- 1.3.6.1.4.1.3715.100.20.2.3
		inputLevelStatus OBJECT-TYPE
			SYNTAX INTEGER
				{
				levelNormal(1),
				levelHIHI(2),
				levelHi(3),
				levelLo(4),
				levelLOLO(5)
				}
			ACCESS read-only
			STATUS mandatory
			DESCRIPTION
				"Input level status:
				1 = normal
				2 = HIHI
				3 = Hi
				4 = Lo
				5 = LOLO"
			::= { downConverter 3 }

		
		-- 1.3.6.1.4.1.3715.100.20.2.4
		inputLnbFrequency OBJECT-TYPE
			SYNTAX INTEGER
			ACCESS read-only
			STATUS optional
			DESCRIPTION
				"LNB local oscillator frequency. Unit 1 MHz."
			::= { downConverter 4 }

		
		-- 1.3.6.1.4.1.3715.100.20.2.5
		inputLnbVoltage OBJECT-TYPE
			SYNTAX INTEGER
			ACCESS read-only
			STATUS optional
			DESCRIPTION
				"LNB or preamplifier voltage. Unit 1 volt."
			::= { downConverter 5 }

		
		-- 1.3.6.1.4.1.3715.100.20.2.6
		inputLnb22kHzControl OBJECT-TYPE
			SYNTAX INTEGER
				{
				off(1),
				on(2)
				}
			ACCESS read-only
			STATUS optional
			DESCRIPTION
				"LNB 22 kHz signal control:
				1 = OFF
				2 = ON"
			::= { downConverter 6 }

		
		-- 1.3.6.1.4.1.3715.100.20.2.7
		inputLnbCurrentStatus OBJECT-TYPE
			SYNTAX INTEGER
				{
				currentNormal(1),
				currentHIHI(2),
				currentHi(3),
				currentLo(4),
				currentLOLO(5)
				}
			ACCESS read-only
			STATUS mandatory
			DESCRIPTION
				"LNB or preamplifier current status:
				1 = normal
				2 = HIHI
				3 = Hi
				4 = Lo
				5 = LOLO"
			::= { downConverter 7 }

		
		-- 1.3.6.1.4.1.3715.100.20.2.8
		inputLnbVoltageControl OBJECT-TYPE
			SYNTAX INTEGER
				{
				off(1),
				on(2)
				}
			ACCESS read-only
			STATUS optional
			DESCRIPTION
				"LNB/preamplifier voltage control:
				1 = OFF
				2 = ON"
			::= { downConverter 8 }

		
		-- 1.3.6.1.4.1.3715.100.20.3
		dvbReceiver OBJECT IDENTIFIER ::= { headEnd 3 }

		
		-- 1.3.6.1.4.1.3715.100.20.3.1
		symbolRateSetting OBJECT-TYPE
			SYNTAX INTEGER
			ACCESS read-write
			STATUS optional
			DESCRIPTION
				"Receiver symbol rate setting. Unit 1 kBd."
			::= { dvbReceiver 1 }

		
		-- 1.3.6.1.4.1.3715.100.20.3.2
		symbolRateMeas OBJECT-TYPE
			SYNTAX INTEGER
			ACCESS read-only
			STATUS mandatory
			DESCRIPTION
				"Measured symbol rate. Unit 1 kBd."
			::= { dvbReceiver 2 }

		
		-- 1.3.6.1.4.1.3715.100.20.3.3
		carrierOffset OBJECT-TYPE
			SYNTAX INTEGER
			ACCESS read-only
			STATUS mandatory
			DESCRIPTION
				"Carrier offset. Unit 1 kHz."
			::= { dvbReceiver 3 }

		
		-- 1.3.6.1.4.1.3715.100.20.3.4
		carrierLockStatus OBJECT-TYPE
			SYNTAX INTEGER
				{
				locked(1),
				unLocked(2)
				}
			ACCESS read-only
			STATUS mandatory
			DESCRIPTION
				"Carrier lock status:
				1 = locked
				2 = unlocked"
			::= { dvbReceiver 4 }

		
		-- 1.3.6.1.4.1.3715.100.20.3.5
		fecStatus OBJECT-TYPE
			SYNTAX INTEGER (0 | 1..8)
			ACCESS read-only
			STATUS mandatory
			DESCRIPTION
				"FEC (Forward Error Correction) status:
				0 = unlocked
				1...8 = Viterbi rate"
			::= { dvbReceiver 5 }

		
		-- 1.3.6.1.4.1.3715.100.20.3.6
		inputSNR OBJECT-TYPE
			SYNTAX INTEGER
			ACCESS read-only
			STATUS mandatory
			DESCRIPTION
				"Estimated input signal to noise ratio. Unit 0.1 dB."
			::= { dvbReceiver 6 }

		
		-- 1.3.6.1.4.1.3715.100.20.3.7
		inputSpectrumStatus OBJECT-TYPE
			SYNTAX INTEGER
				{
				normal(1),
				inverted(2),
				normalManual(3),
				invertedManual(4)
				}
			ACCESS read-only
			STATUS mandatory
			DESCRIPTION
				"Input spectrum status/control:
				1 = normal
				2 = inverted
				3 = normal (manual setting)
				4 = inverted (manual setting)"
			::= { dvbReceiver 7 }

		
		-- 1.3.6.1.4.1.3715.100.20.3.8
		asiLockStatus OBJECT-TYPE
			SYNTAX INTEGER
				{
				locked(1),
				unLocked(2)
				}
			ACCESS read-only
			STATUS mandatory
			DESCRIPTION
				"ASI lock status:
				1 = locked
				2 = unlocked"
			::= { dvbReceiver 8 }

		
		-- 1.3.6.1.4.1.3715.100.20.3.9
		bufferStatus OBJECT-TYPE
			SYNTAX INTEGER
				{
				normal(1),
				overflow(2)
				}
			ACCESS read-only
			STATUS mandatory
			DESCRIPTION
				"Buffer status:
				1 = normal
				2 = overflow"
			::= { dvbReceiver 9 }

		
		-- 1.3.6.1.4.1.3715.100.20.3.10
		contentStatus OBJECT-TYPE
			SYNTAX INTEGER
				{
				detected(1),
				missing(2)
				}
			ACCESS read-only
			STATUS mandatory
			DESCRIPTION
				"Content status:
				1 = detected
				2 = missing"
			::= { dvbReceiver 10 }

		
		-- 1.3.6.1.4.1.3715.100.20.3.11
		sdhStatus OBJECT-TYPE
			SYNTAX INTEGER
				{
				sdhPresent(1),
				sdhMissing(2)
				}
			ACCESS read-only
			STATUS mandatory
			DESCRIPTION
				"SDH input status:
				1 = SDH signal present
				2 = SDH signal missing"
			::= { dvbReceiver 11 }

		
		-- 1.3.6.1.4.1.3715.100.20.3.12
		aal5Status OBJECT-TYPE
			SYNTAX INTEGER
				{
				aal5Normal(1),
				aal5Failure(2)
				}
			ACCESS read-only
			STATUS mandatory
			DESCRIPTION
				"SDH input AAL-5 status:
				1 = AAL-5 layer is OK
				2 = AAL-5 layer has problems"
			::= { dvbReceiver 12 }

		
		-- 1.3.6.1.4.1.3715.100.20.4
		tvModulator OBJECT IDENTIFIER ::= { headEnd 4 }

		
		-- 1.3.6.1.4.1.3715.100.20.4.1
		videoGain OBJECT-TYPE
			SYNTAX INTEGER
			ACCESS read-write
			STATUS optional
			DESCRIPTION
				"Video gain control."
			::= { tvModulator 1 }

		
-- Video sync status.
		-- 1.3.6.1.4.1.3715.100.20.4.2
		videoSyncStatus OBJECT-TYPE
			SYNTAX INTEGER
				{
				sync(1),
				noSync(2)
				}
			ACCESS read-only
			STATUS mandatory
			DESCRIPTION
				"Video sync status:
				1 = in sync
				2 = no sync"
			::= { tvModulator 2 }

		
		-- 1.3.6.1.4.1.3715.100.20.4.3
		videoLevelStatus OBJECT-TYPE
			SYNTAX INTEGER
				{
				levelNormal(1),
				levelHIHI(2),
				levelHi(3),
				levelLo(4),
				levelLOLO(5)
				}
			ACCESS read-only
			STATUS mandatory
			DESCRIPTION
				"Video level status:
				1 = normal
				2 = HIHI
				3 = Hi
				4 = Lo
				5 = LOLO"
			::= { tvModulator 3 }

		
		-- 1.3.6.1.4.1.3715.100.20.4.4
		inputVideoLevelStatus OBJECT-TYPE
			SYNTAX INTEGER
				{
				levelNormal(1),
				levelHIHI(2),
				levelHi(3),
				levelLo(4),
				levelLOLO(5)
				}
			ACCESS read-only
			STATUS mandatory
			DESCRIPTION
				"Video level status:
				1 = normal
				2 = HIHI
				3 = Hi
				4 = Lo
				5 = LOLO"
			::= { tvModulator 4 }

		
		-- 1.3.6.1.4.1.3715.100.20.4.5
		residualCarrierLevel OBJECT-TYPE
			SYNTAX INTEGER
			ACCESS read-only
			STATUS mandatory
			DESCRIPTION
				"Residual carrier value. Unit 0.1 %."
			::= { tvModulator 5 }

		
		-- 1.3.6.1.4.1.3715.100.20.4.6
		residualCarrierStatus OBJECT-TYPE
			SYNTAX INTEGER
				{
				carrierNormal(1),
				carrierHIHI(2),
				carrierHi(3),
				carrierLo(4),
				carrierLOLO(5)
				}
			ACCESS read-only
			STATUS mandatory
			DESCRIPTION
				"Residual carrier status:
				1 = normal
				2 = HIHI
				3 = Hi
				4 = Lo
				5 = LOLO"
			::= { tvModulator 6 }

		
		-- 1.3.6.1.4.1.3715.100.20.5
		dvbModulator OBJECT IDENTIFIER ::= { headEnd 5 }

		
		-- 1.3.6.1.4.1.3715.100.20.5.1
		qamSymbolRate OBJECT-TYPE
			SYNTAX INTEGER
			ACCESS read-write
			STATUS optional
			DESCRIPTION
				"QAM symbol rate. Unit 1 kBd."
			::= { dvbModulator 1 }

		
		-- 1.3.6.1.4.1.3715.100.20.5.2
		qamConstellation OBJECT-TYPE
			SYNTAX INTEGER
				{
				qam16(16),
				qam32(32),
				qam64(64),
				qam128(128),
				qam256(256),
				qam512(512)
				}
			ACCESS read-write
			STATUS optional
			DESCRIPTION
				"QAM constellation:
				16 = 16QAM
				32 = 32QAM
				64 = 64QAM
				128 = 128QAM
				256 = 256QAM
				512 = 512QAM"
			::= { dvbModulator 2 }

		
		-- 1.3.6.1.4.1.3715.100.20.5.3
		qamSpectrumControl OBJECT-TYPE
			SYNTAX INTEGER
				{
				normal(1),
				inverted(2)
				}
			ACCESS read-write
			STATUS optional
			DESCRIPTION
				"Output spectrum control:
				1 = normal
				2 = inverted
				"
			::= { dvbModulator 3 }

		
		-- 1.3.6.1.4.1.3715.100.20.6
		ifAmplifier OBJECT IDENTIFIER ::= { headEnd 6 }

		
		-- 1.3.6.1.4.1.3715.100.20.6.1
		ifLevelStatus OBJECT-TYPE
			SYNTAX INTEGER
				{
				levelNormal(1),
				levelHIHI(2),
				levelHi(3),
				levelLo(4),
				levelLOLO(5)
				}
			ACCESS read-only
			STATUS mandatory
			DESCRIPTION
				"IF level status:
				1 = normal
				2 = HIHI
				3 = Hi
				4 = Lo
				5 = LOLO"
			::= { ifAmplifier 1 }

		
-- If input status
		-- 1.3.6.1.4.1.3715.100.20.6.2
		ifInputStatus OBJECT-TYPE
			SYNTAX INTEGER
				{
				primary(1),
				secondary(2)
				}
			ACCESS read-only
			STATUS mandatory
			DESCRIPTION
				"IF input state:
				1 = primary
				2 = secondary"
			::= { ifAmplifier 2 }

		
		-- 1.3.6.1.4.1.3715.100.20.7
		upConverter OBJECT IDENTIFIER ::= { headEnd 7 }

		
		-- 1.3.6.1.4.1.3715.100.20.7.1
		outputFrequency OBJECT-TYPE
			SYNTAX INTEGER
			ACCESS read-write
			STATUS mandatory
			DESCRIPTION
				"Output frequency. Unit 1 kHz.
				For analogue television signals, the vision carrier frequency.
				For a QAM signal, the centre (carrier) frequency)."
			::= { upConverter 1 }

		
		-- 1.3.6.1.4.1.3715.100.20.7.2
		outputLevel OBJECT-TYPE
			SYNTAX INTEGER
			ACCESS read-write
			STATUS mandatory
			DESCRIPTION
				"Output level. Unit 0.1 dBuV.
				Use of other units is possible depending on the module type."
			::= { upConverter 2 }

		
		-- 1.3.6.1.4.1.3715.100.20.7.3
		outputLevelControlMode OBJECT-TYPE
			SYNTAX INTEGER
				{
				manual(1),
				automatic(2)
				}
			ACCESS read-write
			STATUS mandatory
			DESCRIPTION
				"Ouput level control mode:
				1 = manual
				2 = automatic"
			::= { upConverter 3 }

		
		-- 1.3.6.1.4.1.3715.100.20.7.4
		outputLevelStatus OBJECT-TYPE
			SYNTAX INTEGER
				{
				levelNormal(1),
				levelHIHI(2),
				levelHi(3),
				levelLo(4),
				levelLOLO(5)
				}
			ACCESS read-only
			STATUS mandatory
			DESCRIPTION
				"Output level status:
				1 = normal
				2 = HIHI
				3 = Hi
				4 = Lo
				5 = LOLO"
			::= { upConverter 4 }

		
		-- 1.3.6.1.4.1.3715.100.20.7.5
		outputControl OBJECT-TYPE
			SYNTAX INTEGER
				{
				outputOn(1),
				outputOff(2)
				}
			ACCESS read-write
			STATUS mandatory
			DESCRIPTION
				"Output ON/OFF control:
				1 = ON
				2 = OFF"
			::= { upConverter 5 }

		
		-- 1.3.6.1.4.1.3715.100.20.8
		descrambler OBJECT IDENTIFIER ::= { headEnd 8 }

		
		-- 1.3.6.1.4.1.3715.100.20.8.1
		caModuleStatus OBJECT-TYPE
			SYNTAX INTEGER
				{
				moduleNormal(1),
				moduleRemoved(2),
				moduleFailure(3)
				}
			ACCESS read-only
			STATUS mandatory
			DESCRIPTION
				"Status of the CA module:
				1 = CA module operates normally
				2 = CA module has been removed
				3 = CA module has a failure
				If the device receives a clear program (no CA module is needed,
				the status will be 1."
			::= { descrambler 1 }

		
		-- 1.3.6.1.4.1.3715.100.20.8.2
		descramblerStatus OBJECT-TYPE
			SYNTAX INTEGER
				{
				descrNormal(1),
				descrNoService(2),
				descrRateTooHigh(3),
				descrModuleProblem(4)
				}
			ACCESS read-only
			STATUS mandatory
			DESCRIPTION
				"Descrambler status:
				1 = normal
				2 = PID or service is missing
				3 = data rate is too high
				4 = a problem with the CA module is detected"
			::= { descrambler 2 }

		
		-- 1.3.6.1.4.1.3715.100.20.9
		multiplexer OBJECT IDENTIFIER ::= { headEnd 9 }

		
		-- 1.3.6.1.4.1.3715.100.20.9.1
		ecmStatus OBJECT-TYPE
			SYNTAX INTEGER
				{
				ecmPresent(1),
				ecmMissing(2)
				}
			ACCESS read-only
			STATUS mandatory
			DESCRIPTION
				"ECM stream status:
				1 = normal
				2 = ECM data is missing"
			::= { multiplexer 1 }

		
		-- 1.3.6.1.4.1.3715.100.20.9.2
		dvbPayloadStatus OBJECT-TYPE
			SYNTAX INTEGER
				{
				dvbPresent(1),
				dvbMissing(2)
				}
			ACCESS read-only
			STATUS mandatory
			DESCRIPTION
				"DVB payload status:
				1 = normal
				2 = a payload is missing"
			::= { multiplexer 2 }

		
		-- 1.3.6.1.4.1.3715.100.20.9.3
		serviceStatus OBJECT-TYPE
			SYNTAX INTEGER
				{
				servicePresent(1),
				serviceMissing(2)
				}
			ACCESS read-only
			STATUS mandatory
			DESCRIPTION
				"DVB payload status:
				1 = normal
				2 = a payload is missing"
			::= { multiplexer 3 }

		
		-- 1.3.6.1.4.1.3715.100.20.10
		encoder OBJECT IDENTIFIER ::= { headEnd 10 }

		
		-- 1.3.6.1.4.1.3715.100.20.10.1
		encoderStatus OBJECT-TYPE
			SYNTAX INTEGER
				{
				encoderNormal(1),
				encoderStopped(2),
				encoderError(3)
				}
			ACCESS read-only
			STATUS mandatory
			::= { encoder 1 }

		
	
	END

--
-- TELESTE-HEADEND-MIB.mib
--
