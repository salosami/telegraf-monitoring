--
-- TELESTE-FUNCTIONAL-CATVISOR-MODEM-MIB.mib
-- MIB generated by MG-SOFT Visual MIB Builder 2013 (64-bit) Version 9.0  Build 760
-- Thursday, June 05, 2014 at 13:09:41
--

-- ****************************************************************************
-- Copyright (c) 2003-2014 by:
-- 
-- Teleste Corporation
-- Seponkatu 1
-- FIN-20660 Littoinen, Finland
-- tel. +358 2 2605 611
-- url: http://www.teleste.com
-- 
-- Module Name: TELESTE-FUNCTIONAL-CATVISOR-MODEM-MIB
-- 
-- Description: MIB module describing common objects for a 
--              modem in any Teleste transponder
-- 
-- Revision History:
-- -----------------
-- 2, 5.6.2014, Sami Kuusisto
-- - Added value ranges.
-- 
-- 1, 11.3.2014, Sami Kuusisto
-- - Initial version
-- 
-- ****************************************************************************

	TELESTE-FUNCTIONAL-CATVISOR-MODEM-MIB DEFINITIONS ::= BEGIN
 
		IMPORTS
			OBJECT-TYPE			
				FROM RFC-1212			
			IpAddress			
				FROM RFC1155-SMI			
			functional			
				FROM TELESTE-ROOT-MIB;
	
	
	
--
-- Node definitions
--
	
		-- 1.3.6.1.4.1.3715.100.8
		catvisorModem OBJECT IDENTIFIER ::= { functional 8 }

		
-- Transponder RF modem specific objects
-- 
		-- 1.3.6.1.4.1.3715.100.8.1
		catvisorModemSettings OBJECT IDENTIFIER ::= { catvisorModem 1 }

		
		-- 1.3.6.1.4.1.3715.100.8.1.1
		catvisorModemRxScanMin OBJECT-TYPE
			SYNTAX INTEGER (0..200000000)
			ACCESS read-write
			STATUS mandatory
			DESCRIPTION
				"Modem receive scanning minimum frequency. Unit 1 kHz."
			::= { catvisorModemSettings 1 }

		
		-- 1.3.6.1.4.1.3715.100.8.1.2
		catvisorModemRxScanMax OBJECT-TYPE
			SYNTAX INTEGER (0..200000000)
			ACCESS read-write
			STATUS mandatory
			DESCRIPTION
				"Modem receive scanning maximum frequency. Unit 1 kHz."
			::= { catvisorModemSettings 2 }

		
		-- 1.3.6.1.4.1.3715.100.8.1.3
		catvisorModemRxScanEnable OBJECT-TYPE
			SYNTAX INTEGER
				{
				scanEnabled(1),
				scanDisabled(2)
				}
			ACCESS read-write
			STATUS mandatory
			DESCRIPTION
				"Modem forward data channel scanning control:
				1 = scanning is enabled
				2 = scanning is disabled (fixed frequency operation)"
			::= { catvisorModemSettings 3 }

		
		-- 1.3.6.1.4.1.3715.100.8.1.4
		catvisorModemTxLevelMin OBJECT-TYPE
			SYNTAX INTEGER (0..20000)
			ACCESS read-write
			STATUS mandatory
			DESCRIPTION
				"Modem minimum transmit level. 
				Unit 0.01 dBµV."
			::= { catvisorModemSettings 4 }

		
		-- 1.3.6.1.4.1.3715.100.8.1.5
		catvisorModemTxLevelMax OBJECT-TYPE
			SYNTAX INTEGER (0..20000)
			ACCESS read-write
			STATUS mandatory
			DESCRIPTION
				"Modem maximum transmit level. 
				Unit 0.01 dBµV.
				"
			::= { catvisorModemSettings 5 }

		
		-- 1.3.6.1.4.1.3715.100.8.1.6
		catvisorModemDeviceGroup OBJECT-TYPE
			SYNTAX INTEGER (0..255)
			ACCESS read-write
			STATUS mandatory
			DESCRIPTION
				"Device group(s). Can be any combination (sum of) of groups 1...8.
				
				Device group 1: 1
				Device group 2: 2
				Device group 3: 4
				Device group 4: 8
				Device group 5: 16
				Device group 6: 32
				Device group 7: 64
				Device group 8: 128"
			::= { catvisorModemSettings 6 }

		
		-- 1.3.6.1.4.1.3715.100.8.1.7
		catvisorModemNetmask OBJECT-TYPE
			SYNTAX IpAddress
			ACCESS read-write
			STATUS mandatory
			DESCRIPTION
				"Netmask. Used only for broadcast software updates."
			::= { catvisorModemSettings 7 }

		
	
	END

--
-- TELESTE-FUNCTIONAL-CATVISOR-MODEM-MIB.mib
--
