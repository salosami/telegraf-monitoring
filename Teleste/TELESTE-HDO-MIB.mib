--
-- TELESTE-HDO-MIB.mib
-- MIB generated by MG-SOFT Visual MIB Builder 2020 (64-bit) Version 14.00  Build 1400
-- Friday, March 27, 2020 at 13:41:27
--

-- ****************************************************************************
-- Copyright (c) 2005-2013 by:
-- 
-- Teleste Corporation
-- Telestenkatu 1
-- FI-20660 Littoinen, Finland
-- tel. +358 2 2605 611
-- url: http://www.teleste.com
-- 
-- Description: HDO module definitions. Note! This MIB only contains sysOID 
-- definitions for HDO modules. All active objects are defined in relevant
-- HMS HEADEND and Teleste enterprise MIBs, mainly the TELESTE-HFCOPTICS-MIB.
-- 
-- Revision History:
-- -----------------
-- 4 27.3.2020, Sami Kuusisto
-- - Renamed virtual-HDM1xxs to VDM1xx (VDM100 T, VDM100 H, VDM155).
-- 
-- 3 6.2.2020, Sami Kuusisto
-- - Added sysOIDs for HDM155, virtual-HDM100T, virtual-HDM100H and virtual-HDM155.
-- 
-- 2 19.3.2018, Sami Kuusisto
-- - Added hdc100ipSettingsStatus and hdm100ipSettingsStatus to HDC100&HDM100.
-- 
-- 1.44 6.3.2018 Sami Kuusisto
-- - Added HDO206, HDO212, HDO613, HDO761, HDO773, HDO774, HDO775, HDO777, HDO803, HDO921, HDO922 and HDO961 sysOIDs.
-- 
-- 1.43 26.6.2015 Sami Kuusisto and Rainer Salminen
-- - Added HDO702, HDO907 and HDO908 sysOIDs.
-- 
-- 1.42 7.8.2013 Matti Susi
-- - corrected errors in modules and oemodules OIDs
-- 
-- 1.41 2.10.2012 Matti Susi
-- - changed HDO720 sysOID label
-- 
-- 1.4 20.8.2012 Matti Susi
-- - added several new sysOIDs
-- 
-- 1.3 27.9.2011 Matti Susi
-- - added HDO718 and HDO721 sysOIDs
-- 
-- 1.2 12.10.2010 Matti Susi
-- - moved sysOIDs here from HDOEDFA-MIB
-- - removed unnecessary sysOIDs
-- 
-- 1.1, 20.2.2009 Matti Susi
-- - added new sysOIDs
-- 
-- 1.0, 13.9.2007 Matti Susi
-- - first offcial version
-- 
-- ****************************************************************************

	TELESTE-HDO-MIB DEFINITIONS ::= BEGIN
 
		IMPORTS
			OBJECT-TYPE			
				FROM RFC-1212			
			teleste			
				FROM TELESTE-ROOT-MIB;
	
	
	
--
-- Node definitions
--
	
-- Root for HDO product definitions.
		-- 1.3.6.1.4.1.3715.14
		hdo OBJECT IDENTIFIER ::= { teleste 14 }

		
-- Object identifier for own HDO modules
		-- 1.3.6.1.4.1.3715.14.1
		modules OBJECT IDENTIFIER ::= { hdo 1 }

		
-- Object identifier for OEM HDO modules
		-- 1.3.6.1.4.1.3715.14.2
		oemodules OBJECT IDENTIFIER ::= { hdo 2 }

		
-- Placeholder for HDC100 sysOID
		-- 1.3.6.1.4.1.3715.14.100
		hdc100 OBJECT IDENTIFIER ::= { hdo 100 }

		
		-- 1.3.6.1.4.1.3715.14.100.6
		hdc100ipSettingsStatus OBJECT-TYPE
			SYNTAX INTEGER
				{
				ipSettingsStatusOk(1),
				ipSettingsStatusInvalid(2),
				ipSettingsStatusNA(3)
				}
			ACCESS read-only
			STATUS mandatory
			DESCRIPTION
				"HDC100 IP settings status."
			::= { hdc100 6 }

		
		-- 1.3.6.1.4.1.3715.14.101
		hdm100 OBJECT IDENTIFIER ::= { hdo 101 }

		
		-- 1.3.6.1.4.1.3715.14.101.6
		hdm100ipSettingsStatus OBJECT-TYPE
			SYNTAX INTEGER
				{
				ipSettingsStatusOk(1),
				ipSettingsStatusInvalid(2),
				ipSettingsStatusNA(3)
				}
			ACCESS read-only
			STATUS mandatory
			DESCRIPTION
				"HDM100 IP settings status."
			::= { hdm100 6 }

		
-- Virtual HDM100 T - VDM100 T - Virtual HEC
		-- 1.3.6.1.4.1.3715.14.102
		vdm100t OBJECT IDENTIFIER ::= { hdo 102 }

		
-- Virtual HDM100 H - VDM100 H - Virtual HMTS
		-- 1.3.6.1.4.1.3715.14.103
		vdm100h OBJECT IDENTIFIER ::= { hdo 103 }

		
-- Virtual HDM155 - VDM155 - Virtual RIS controller
		-- 1.3.6.1.4.1.3715.14.104
		vdm155 OBJECT IDENTIFIER ::= { hdo 104 }

		
		-- 1.3.6.1.4.1.3715.14.105
		hdm155 OBJECT IDENTIFIER ::= { hdo 105 }

		
		-- 1.3.6.1.4.1.3715.14.111
		hdo101 OBJECT IDENTIFIER ::= { hdo 111 }

		
		-- 1.3.6.1.4.1.3715.14.151
		hdo151 OBJECT IDENTIFIER ::= { hdo 151 }

		
-- Placeholder for HDO202 sysOID
		-- 1.3.6.1.4.1.3715.14.202
		hdo202 OBJECT IDENTIFIER ::= { hdo 202 }

		
-- Placeholder for HDO203 sysOID
		-- 1.3.6.1.4.1.3715.14.203
		hdo203 OBJECT IDENTIFIER ::= { hdo 203 }

		
		-- 1.3.6.1.4.1.3715.14.204
		hdo204 OBJECT IDENTIFIER ::= { hdo 204 }

		
		-- 1.3.6.1.4.1.3715.14.205
		hdo205 OBJECT IDENTIFIER ::= { hdo 205 }

		
		-- 1.3.6.1.4.1.3715.14.206
		hdo206 OBJECT IDENTIFIER ::= { hdo 206 }

		
		-- 1.3.6.1.4.1.3715.14.212
		hdo212 OBJECT IDENTIFIER ::= { hdo 212 }

		
-- Placeholder for HDP230 sysOID
		-- 1.3.6.1.4.1.3715.14.230
		hdp230 OBJECT IDENTIFIER ::= { hdo 230 }

		
		-- 1.3.6.1.4.1.3715.14.272
		hdo272 OBJECT IDENTIFIER ::= { hdo 272 }

		
-- Placeholder for HDP301 sysOID
		-- 1.3.6.1.4.1.3715.14.301
		hdp301 OBJECT IDENTIFIER ::= { hdo 301 }

		
-- Placeholder for HDO302 sysOID
		-- 1.3.6.1.4.1.3715.14.302
		hdo302 OBJECT IDENTIFIER ::= { hdo 302 }

		
-- Placeholder for HDO371 sysOID
		-- 1.3.6.1.4.1.3715.14.371
		hdo371 OBJECT IDENTIFIER ::= { hdo 371 }

		
-- Placeholder for HDO421 sysOID
		-- 1.3.6.1.4.1.3715.14.421
		hdo421 OBJECT IDENTIFIER ::= { hdo 421 }

		
-- Placeholder for HDO610 sysOID
		-- 1.3.6.1.4.1.3715.14.610
		hdo610 OBJECT IDENTIFIER ::= { hdo 610 }

		
		-- 1.3.6.1.4.1.3715.14.611
		hdo611 OBJECT IDENTIFIER ::= { hdo 611 }

		
		-- 1.3.6.1.4.1.3715.14.613
		hdo613 OBJECT IDENTIFIER ::= { hdo 613 }

		
-- Placeholder for HDO700P sysOID
		-- 1.3.6.1.4.1.3715.14.700
		hdo700p OBJECT IDENTIFIER ::= { hdo 700 }

		
-- Placeholder for HDO701 sysOID
		-- 1.3.6.1.4.1.3715.14.701
		hdo701 OBJECT IDENTIFIER ::= { hdo 701 }

		
		-- 1.3.6.1.4.1.3715.14.702
		hdo702 OBJECT IDENTIFIER ::= { hdo 702 }

		
		-- 1.3.6.1.4.1.3715.14.702.4
		transmitter OBJECT IDENTIFIER ::= { hdo702 4 }

		
		-- 1.3.6.1.4.1.3715.14.702.10
		powersupply OBJECT IDENTIFIER ::= { hdo702 10 }

		
-- Placeholder for HDO716 sysOID
		-- 1.3.6.1.4.1.3715.14.716
		hdo716 OBJECT IDENTIFIER ::= { hdo 716 }

		
-- Placeholder for HDO719 sysOID
		-- 1.3.6.1.4.1.3715.14.719
		hdo719 OBJECT IDENTIFIER ::= { hdo 719 }

		
		-- 1.3.6.1.4.1.3715.14.720
		hdo72x series OBJECT IDENTIFIER ::= { hdo 720 }

		
-- Placeholder for HDO722 sysOID
		-- 1.3.6.1.4.1.3715.14.722
		hdo722 OBJECT IDENTIFIER ::= { hdo 722 }

		
-- Placeholder for HDO724 sysOID
		-- 1.3.6.1.4.1.3715.14.724
		hdo724 OBJECT IDENTIFIER ::= { hdo 724 }

		
-- Placeholder for HDO726 sysOID
		-- 1.3.6.1.4.1.3715.14.726
		hdo726 OBJECT IDENTIFIER ::= { hdo 726 }

		
-- Placeholder for HDO726 sysOID
		-- 1.3.6.1.4.1.3715.14.729
		hdo729 OBJECT IDENTIFIER ::= { hdo 729 }

		
		-- 1.3.6.1.4.1.3715.14.732
		hdo732 OBJECT IDENTIFIER ::= { hdo 732 }

		
		-- 1.3.6.1.4.1.3715.14.735
		hdo735 OBJECT IDENTIFIER ::= { hdo 735 }

		
		-- 1.3.6.1.4.1.3715.14.736
		hdo736 OBJECT IDENTIFIER ::= { hdo 736 }

		
		-- 1.3.6.1.4.1.3715.14.750
		hdo750 OBJECT IDENTIFIER ::= { hdo 750 }

		
		-- 1.3.6.1.4.1.3715.14.761
		hdo761 OBJECT IDENTIFIER ::= { hdo 761 }

		
		-- 1.3.6.1.4.1.3715.14.771
		hdo771 OBJECT IDENTIFIER ::= { hdo 771 }

		
		-- 1.3.6.1.4.1.3715.14.772
		hdo772 OBJECT IDENTIFIER ::= { hdo 772 }

		
		-- 1.3.6.1.4.1.3715.14.773
		hdo773 OBJECT IDENTIFIER ::= { hdo 773 }

		
		-- 1.3.6.1.4.1.3715.14.774
		hdo774 OBJECT IDENTIFIER ::= { hdo 774 }

		
		-- 1.3.6.1.4.1.3715.14.775
		hdo775 OBJECT IDENTIFIER ::= { hdo 775 }

		
		-- 1.3.6.1.4.1.3715.14.776
		hdo776 OBJECT IDENTIFIER ::= { hdo 776 }

		
		-- 1.3.6.1.4.1.3715.14.777
		hdo777 OBJECT IDENTIFIER ::= { hdo 777 }

		
-- Placeholder for HDO802 sysOID
		-- 1.3.6.1.4.1.3715.14.802
		hdo802 OBJECT IDENTIFIER ::= { hdo 802 }

		
		-- 1.3.6.1.4.1.3715.14.803
		hdo803 OBJECT IDENTIFIER ::= { hdo 803 }

		
-- Placeholder for HDO902 sysOID
		-- 1.3.6.1.4.1.3715.14.902
		hdo902 OBJECT IDENTIFIER ::= { hdo 902 }

		
-- Placeholder for HDO903 sysOID
		-- 1.3.6.1.4.1.3715.14.903
		hdo903 OBJECT IDENTIFIER ::= { hdo 903 }

		
		-- 1.3.6.1.4.1.3715.14.904
		hdo904 OBJECT IDENTIFIER ::= { hdo 904 }

		
		-- 1.3.6.1.4.1.3715.14.905
		hdo905 OBJECT IDENTIFIER ::= { hdo 905 }

		
		-- 1.3.6.1.4.1.3715.14.906
		hdo906 OBJECT IDENTIFIER ::= { hdo 906 }

		
		-- 1.3.6.1.4.1.3715.14.907
		hdo907 OBJECT IDENTIFIER ::= { hdo 907 }

		
		-- 1.3.6.1.4.1.3715.14.908
		hdo908 OBJECT IDENTIFIER ::= { hdo 908 }

		
		-- 1.3.6.1.4.1.3715.14.921
		hdo921 OBJECT IDENTIFIER ::= { hdo 921 }

		
		-- 1.3.6.1.4.1.3715.14.922
		hdo922 OBJECT IDENTIFIER ::= { hdo 922 }

		
		-- 1.3.6.1.4.1.3715.14.961
		hdo961 OBJECT IDENTIFIER ::= { hdo 961 }

		
	
	END

--
-- TELESTE-HDO-MIB.mib
--
